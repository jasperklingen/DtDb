FME workspace SOV.fmw

Parameters:
- SHOPPINGCART_UUID =   # ShoppingCart UUID
- SELECTED_GROUP_NAME =   # Selected Group Name
- CONFIG_XLSX = C:\Users\OscarWillemsAvineon-\Downloads\B10.0_SOV_150kV_Configuration.xlsx   # Config
- SELECTED_GROUP = http://data.tennet.eu/id/e42da9eb-8f2e-f111-b6d1-001dd8d702ae   # Selected Group
- COPIES = 1   # Number of Copies
- SPARQL_OUTFOLDER = $(FME_SHAREDRESOURCE_TEMP)   # Temp folder for SPARQL result
- HubLaces =   # AUTH_NAMED_CONNECTION Hub Laces
- AUTH_NAMED_CONNECTION = TenneT Laces
- Relatics =
- TARGET_URL = https://tennet.relaticsonline.com/DataExchange.asmx?wsdl   # Request URL
- RelaticsWorkspace = niet-bestaande-UUID   # Relatics Workspace
- BATCH_SIZE = 1000   # Batch Size for Relatics (0 for no batch)
- REPORT_YESNO = Yes   # Report of Relatics Import
- HEADER = H3   # Validation Header Level
- RETRY_INITIAL_BACKOFF = 5000   # Initial Backoff Time (msec)
- RATE_LIMIT_MAX_REQUESTS = 200   # Maximum Requests per Interval
- FME_SHAREDRESOURCE_TEMP = C:\Users\OscarWillemsAvineon-\OneDrive - Tensing\Documents\Consultancy\TenneT\SOV\SOV   # FME Flow Temporary Resource Directory

Readers:
- XLSXR_1: XLSXR from $(CONFIG_XLSX)

Writers:
- HTML_1: HTML to $(SPARQL_OUTFOLDER)\$(RelaticsWorkspace)

Note: This script reads a Config Files with queries that need to be run on Linked Data platform Laces using SPARQL / The user input is: / - a selected group from a a (dynamic) tree structure (asset group decomposition) / - a number of instances to make of this group / - Config Excel with queries / The script will check the selected object is still present within the tree (in case of the Scripted Selection this step is not necesary) / For the decomposition query the selected group is queried for its child parts recursively (GetSOVChildren) and unique concepts are saved. / Then an InlineQuerier is used to complete the decomposition by adding recurring paths (multiple assets might have an object with the same subcomponents). / Each object gets an UUID to be an object. / Then for each concept the metadata/aspects/verificationplans/etc. is queried and the result is joined on the objects based on the type of object it is. / The result is dynamically written to an XML-based import file for the SOAP service of Relatics
Note: http://data.tennet.eu/id/51ace467-50ff-ef11-b6c1-001dd8d702b3
Note: Group with only RealObjects in the decomposition / http://data.tennet.eu/id/d0ba538f-ec66-f011-b6c5-001dd8d702ae / Group with Containers within the path:

Bookmark: Read Config
SOVQuerys (reader XLSXR_1)
    attributes: Order number(2,0), Query char(2515), QueryName char(22), QueryEndpoint char(79), Filename char(74), Operation char(70), Entrycode char(32)
    -> Tester_10
Tester_10
    BOOL_OP = OR
    TEST_CLAUSE = TEST Query ATTRIBUTE_HAS_A_VALUE ""
    TEST_MODE = TEST
    PASSED -> StringReplacer_8
    FAILED -> Junction_9
StringReplacer_8
    CASE = NO
    FIND_TEXT = "\n"
    NO_MATCH = _FME_NO_OP_
    REGEXP = NO
    SRC_ATTRS = Entrycode,Filename,Operation,QueryEndpoint,QueryName
    -> AttributeFilter_3
AttributeFilter_3
    ATTR_NAME = QueryName
    ATTR_VALUES = <Empty>,<Missing>,<Null>,Tree,Publication,<Unfiltered>
    Tree -> DuplicateFilter
    Publication -> DuplicateFilter_4
    <UNFILTERED> -> StringSearcher_5
    <UNFILTERED> -> Junction_5
Note: Relatics: FeatureMerger_3
Junction_5
    -> Junction_8
Note: emptry Excel rows
Junction_9

Bookmark: Selected Group
DuplicateFilter
    INPUT_ORDERED_CHOICE_LOOKUP = NO
    KEYATTR = Query QueryName
    INPUT_ORDERED_CHOICE = No
    UNIQUE -> ParameterFetcher
ParameterFetcher
    ATTR_LIST = _SelectedGroup $(SELECTED_GROUP)
    -> FeatureMerger [REQUESTOR]

Bookmark: 3.2 Pre-Proces Data for Relatics
Note: Queries not tree
Junction_8
    -> FeatureMerger_3 [SUPPLIER]
Note: Generic Queries
Junction_15
    -> PythonCaller
Note: Loop through attribute{}.name Remove & and < from attributes values if it has a value
PythonCaller
    PYTHONSOURCE:
      import fme
      import fmeobjects


      class FeatureProcessor(object):
          """Template Class Interface:
          When using this class, make sure its name is set as the value of the 'Class
          to Process Features' transformer parameter.
          """

          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              sparqlheaders = feature.getAttribute('attribute{}.name')
              for h in sparqlheaders:
                  ### bugfix: string() makes sure that an attribute is always
                  ### replaceable, in case attribute contains only numbers
                  att = feature.getAttribute(h)
                  if att is None:
                      pass
                  else:
                      att = str(att)
                      new1 = att.replace('&','&amp;')
                      new2 = new1.replace('<','&lt;')
                      feature.setAttribute(h,new2)

              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> PythonCaller_3
Note: SPARQL CSV row to RelaticsXML Row
PythonCaller_3
    NEW_ATTRIBUTES = _xmlline
    PYTHONSOURCE:
      import fme
      import fmeobjects
      from fmeobjects import FMELogFile
      import re


      class FeatureProcessor(object):
          """Template Class Interface:
          When using this class, make sure its name is set as the value of the 'Class
          to Process Features' transformer parameter.
          """

          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              ## Add attributes to <Row>
              schema = feature.getAttribute('attribute{}.name')
              xmlpart = []
              for attribute in schema:
                 value = feature.getAttribute(attribute)
                 value_str = "" if value is None else str(value)
                 xmlpart.append(attribute.replace("?","")+'="'+re.sub(r'"','',value_str)+'"')

              ## Add publication attributes to <Row>
              publication = feature.getAttribute('publicationHeaders{}.name')
              if publication:
                  for attribute in publication:
                     value = feature.getAttribute(attribute)
                     value_str = "" if value is None else str(value)
                     xmlpart.append(attribute.replace("?","")+'="'+re.sub(r'"','',value_str)+'"')

              ## Create <Row>
              xmlline = "<Row "+" ".join(xmlpart)+" />"

              feature.setAttribute('_xmlline',xmlline)
              ##FMELogFile().logMessageString(xmlline,2)
              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> Tester_2
Note: BatchSize = 0
Tester_2
    BOOL_OP = OR
    TEST_CLAUSE = TEST $(BATCH_SIZE) = 0
    TEST_MODE = TEST
    PASSED -> AttributeCreator_9
    FAILED -> BatchGrouper
AttributeCreator_9
    ATTR_TABLE = SET_TO temp_filename = @Value(Filename)
    -> FeatureWriter_2 [text_line]
BatchGrouper
    DOMAIN = @Value(Operation)
    GROUP_SIZE = $(BATCH_SIZE)
    VAL_ATTR = _group
    -> StringReplacer_3
StringReplacer_3
    CASE = NO
    FIND_TEXT = \.xml$<pipe>\.csv$
    NO_MATCH = _FME_NO_OP_
    REGEXP = YES
    SRC_ATTRS = Filename
    -> AttributeCreator
Note: AttributeCreator [AttributeCreator] / Attributes To Create: New AttributeValuetemp_filename@Value(Filename)_batch$(BATCH_SIZE)-@Value(_group).xml
AttributeCreator
    ATTR_TABLE = SET_TO temp_filename = @Value(Filename)_batch$(BATCH_SIZE)-@Value(_group).xml
    -> FeatureWriter_2 [text_line]
FeatureWriter_2
    DATASET = $(SPARQL_OUTFOLDER)/$(RelaticsWorkspace)/@Value(temp_filename)
    DATASET_ATTR = _dataset
    FEATURE_TYPE_LIST_ATTR = _feature_types
    FORMAT = TEXTLINE
    GROUP_BY = Entrycode Filename Operation
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = text/plain
    TEXTLINE_NETWORK_AUTHENTICATION = AUTH_INFO_GROUP,NO,AUTH_METHOD,<Unused>,NAMED_CONNECTION,<Unused>,AUTH_USERNAME,<Unused>,AUTH_PASSWORD,<Unused>
    TEXTLINE_OVERWRITE_FILE = YES
    TEXTLINE_WRITE_LAST_EOL = YES
    TEXTLINE_WRITE_UTF8_BOM = YES
    TOTAL_FEATURES_WRITTEN_ATTR = _total_features_written
    SUMMARY -> FilenamePartExtractor
FilenamePartExtractor
    DIRNAME_ATTR = _dirname
    DIRPATH_ATTR = _dirpath
    EXTENSION_ATTR = _extension
    FULLNAME_ATTR = Filename
    ROOTNAME_ATTR = JoinKey
    SRC_ATTR = @Value(_dataset)
    -> StringSearcher_6
StringSearcher_6
    CASE = no
    MATCHED_RESULT_ATTR = _first_match
    REGEXP = _batch\d+-\d+$
    STRING_TO_SEARCH = @Value(JoinKey)
    MATCHED -> StringReplacer_7
    NOT_MATCHED -> AttributeCreator_10
AttributeCreator_10
    ATTR_TABLE = SET_TO JoinKey (buffer) = @Value(JoinKey).xml
    -> FeatureMerger_3 [REQUESTOR]
StringReplacer_7
    CASE = NO
    FIND_TEXT = @Value(_first_match)
    NO_MATCH = _FME_NO_OP_
    REGEXP = NO
    REPLACE_TEXT = .xml
    SRC_ATTRS = JoinKey
    -> FeatureMerger_3 [REQUESTOR]
FeatureMerger_3
    ATTR_ACCUM_MODE = Merge Supplier
    ATTR_CONFLICT_RES_LOOKUP = REQUESTOR_IF_CONFLICT
    IGNORE_NULLS = No
    JOIN_KEYS = @Value(JoinKey) @Value(Filename) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeFileReader
AttributeFileReader
    CHAR_ENCODING = utf-8
    DEST_ATTR = _file_contents
    FILE_NAME = @Value(_dataset)
    -> AttributeCreator_6
Note: AttributeCreator_6 [AttributeCreator] / Attributes To Create: New AttributeValueRelaticsDataXML<import> / @Value(_file_contents) / </import>
AttributeCreator_6
    ATTR_TABLE:
      SET_TO RelaticsDataXML = <import>
        @Value(_file_contents)
        </import>
    -> Sorter_3
Sorter_3
    SORT_PARM = Order NUMERIC ASCENDING Operation NATURAL ASCENDING Filename NATURAL ASCENDING
    SORTED -> TextEncoder_2

Bookmark: Decomposition Queries (Spaces/Objects)
Note: Find type of object/space
StringSearcher_5
    CASE = no
    MATCHED_RESULT_ATTR = type
    MATCHES_ATTR = _allmatch
    REGEXP = Object<pipe>Space
    STRING_TO_SEARCH = @Value(QueryName)
    MATCHED -> AttributeFilter_4
    NOT_MATCHED -> DuplicateFilter_5
Note: Decomposition Queries
AttributeFilter_4
    ATTR_NAME = QueryName
    ATTR_VALUES = <Empty>,<Missing>,<Null>,GetChildSpace,GetChildObject,<Unfiltered>
    GetChildSpace -> FeatureMerger [SUPPLIER]
    GetChildObject -> FeatureMerger [SUPPLIER]
    <UNFILTERED> -> Tester_5

Bookmark: Get Queries ready for Selected Group
FeatureMerger
    ATTR_ACCUM_MODE = Merge Supplier
    ATTR_CONFLICT_RES_LOOKUP = SUPPLIER_IF_CONFLICT
    IGNORE_NULLS = No
    JOIN_KEYS = 1 1 AUTO
    LIST_ATTRS_TO_INCLUDE = Entrycode Filename Operation Order Query QueryEndpoint QueryName type
    LIST_NAME = _input
    MERGE_TYPE_VAL = ATTRIBUTES
    PROCESS_DUPS = NO
    REJECT_NULL_MISSING_KEYS = No
    SUPPLIERS_FIRST = No
    ATTR_CONFLICT_RES = Use Supplier
    MERGE_TYPE = Attributes Only
    MERGED -> ListExploder_2
    UNUSED_SUPPLIER -> Sampler
ListExploder_2
    ATTR_CONFLICT_RES_LOOKUP = INCOMING_IF_CONFLICT
    INDEX_ATTR = _element_index
    LIST_ATTR = _input{}
    ATTR_ACCUM_MODE = Merge List Attributes
    ATTR_CONFLICT_RES = Use List Attribute Values
    ELEMENTS -> AttributeCreator_2
Sampler
    MODE = ORIGINAL
    RATE = 1
    SAMPLE_TYPE_MULTIPLIER = -1
    SAMPLE_MODE = No
    SAMPLE_TYPE_LONG = First N Features
    SAMPLED -> Logger_2
Logger_2
    LOG_FEATURE = NONE
    MAXFEATS = 20
    MESSAGE = Selected Group <$(SELECTED_GROUP)> does not return a valid selection!
    SEVERITY = ERROR
Tester_5
    BOOL_OP = OR
    TEST_CLAUSE:
      CASE_INSENSITIVE_TEST @Value(QueryName) ENDS_WITH Object
      CASE_INSENSITIVE_TEST @Value(QueryName) ENDS_WITH Space
    TEST_MODE = TEST
    PASSED -> Junction_10

Bookmark: New Bookmark
AttributeCreator_2
    ATTR_TABLE:
      SET_TO _path (varchar(200)) = SELECTED GROUP @Value(_SelectedGroup)
      SET_TO _level (varchar(200)) = 0
    -> AttributeKeeper
AttributeKeeper
    CREATE_BULK_MODE_FEATURES = NO
    KEEP_ATTRS = _level,_SelectedGroup,_path,child,childName,Filename,Operation,Order,Query,Entrycode,QueryName,QueryEndpoint,type
    -> Junction_7

Bookmark: Get Objects/Spaces for selected Group
Note: Runtime: / 1: FeatureMerger / 2: GetSOVChildren
Junction_7
    -> AttributeRenamer_2
    -> GetSOVChildren
AttributeRenamer_2
    ATTR_TABLE:
      RENAME_SET_DEFAULT child > parent
      RENAME_SET_DEFAULT childName > parentName
    KEEP_RENAMED_ONLY = no
    MISSING_INPUT_ATTRS = REMOVE
    -> AttributeKeeper_2
AttributeKeeper_2
    CREATE_BULK_MODE_FEATURES = NO
    KEEP_ATTRS = Filename,Operation,Entrycode,type
    -> FeatureMerger_2 [SUPPLIER]
GetSOVChildren
    AUTH_NAMED_CONNECTION = $(AUTH_NAMED_CONNECTION)
    RATE_LIMIT_MAX_REQUESTS = $(RATE_LIMIT_MAX_REQUESTS)
    RETRY_INITIAL_BACKOFF = $(RETRY_INITIAL_BACKOFF)
    TARGET_URL = @Value(QueryEndpoint)
    _LEVEL = @Value(_level)
    _PATH = @Value(_path)
    _QUERY = @Value(Query)
    _SELECTEDGROUP = @Value(_SelectedGroup)
    UniqueChild -> AttributeKeeper_5
    UniqueChild -> Tester_3
    DuplicateChild -> AttributeKeeper_5
    <Rejected> -> Junction_3
AttributeKeeper_5
    CREATE_BULK_MODE_FEATURES = NO
    KEEP_ATTRS = child,childName,parent,Operation,childType,parentName,parentType
    -> InlineQuerier_2 [AllConcepts]
Note: https://chatgpt.com/share/68814803-f944-800d-9061-3a32f60565c0
InlineQuerier_2
    QUERY_DEF:
      Objects,WITH RECURSIVE ConceptTree(
        child,
        childName,
        childType,
        parent,
        parentName,
        parentType,
        depth,
        path,
        Operation
      ) AS (
        -- Base case: select root nodes (nodes that are never a child)
        SELECT
          ac.child,
          ac.childName,
          ac.childType,
          ac.parent,
          ac.parentName,
          ac.parentType,
          0 AS depth,
          ac.child <pipe><pipe> ' ' <pipe><pipe> ac.childName <pipe><pipe> ' ' <pipe><pipe> ac.childType AS path,
          ac.Operation
        FROM AllConcepts ac
        WHERE ac.parent NOT IN (SELECT child FROM AllConcepts)

        UNION ALL

        -- Recursive case: find children of previous level
        SELECT
          ac.child,
          ac.childName,
          ac.childType,
          ac.parent,
          ac.parentName,
          ac.parentType,
          ct.depth + 1 AS depth,
          ct.path <pipe><pipe> '<pipe>' <pipe><pipe> ac.child <pipe><pipe> ' ' <pipe><pipe> ac.childName <pipe><pipe> ' ' <pipe><pipe> ac.childType AS path,
          ac.Operation
        FROM AllConcepts ac
        JOIN ConceptTree ct ON ac.parent = ct.child
      )

      SELECT DISTINCT child, childName, childType, parent, parentName, parentType, depth, path, Operation
      FROM ConceptTree
      -- Remove container objects and only keep RealObjects/Spaces
      WHERE 1=1
      -- and not childType like '%Container'
      ORDER BY depth, path;
      ,FIRST
    QUERY_SCHEMA = Objects,child,varchar(61),childName,varchar(50),childType,varchar(20),parent,varchar(61),parentName,varchar(26),parentType,varchar(26),depth,,path,,Operation,varchar(26)
    TABLE_DEF = AllConcepts,child,varchar(61),childName,varchar(50),childType,varchar(20),parent,varchar(61),parentName,varchar(26),parentType,varchar(26),Operation,varchar(26)
    Objects -> Cloner
Note: Create X Copies based on User Parameter
Cloner
    COPIES = $(COPIES)
    COPYATT = _copynum
    COPY -> DuplicateFilter_2
Note: Containers komen uit Space & Object queries
DuplicateFilter_2
    INPUT_ORDERED_CHOICE_LOOKUP = NO
    KEYATTR = _copynum child childName childType depth parent parentName parentType path
    INPUT_ORDERED_CHOICE = No
    UNIQUE -> UniqueIdentifierGenerator_3
Note: Generate UUID for each Real Object
UniqueIdentifierGenerator_3
    UUID_ATTR = foreignKey
    UUID_FORMAT = UUID_ONLY
    -> Tester_6
Tester_6
    BOOL_OP = OR
    TEST_CLAUSE = TEST @Value(childType) NOT_= http://www.w3.org/2000/01/rdf-schema#Container
    TEST_MODE = TEST
    PASSED -> AttributeCopier_3
    PASSED -> AttributeKeeper_10
Note: parent_path
AttributeCopier_3
    ATTR_TABLE = COPY path > parent_path
    MISSING_INPUT_ATTRS = REMOVE
    -> StringReplacer_11
Note: Remove last path after |
StringReplacer_11
    CASE = NO
    FIND_TEXT = [^<pipe>]+$
    NO_MATCH = _FME_NO_OP_
    REGEXP = YES
    SRC_ATTRS = parent_path
    -> AttributeTrimmer_4
Note: Trim |
AttributeTrimmer_4
    SRC_ATTRS = parent_path
    TRIM_CHARS = <pipe>
    TRIM_TO_NONE = Yes
    TRIM_TYPE = BOTH
    -> PythonCaller_4
Note: While parent_path end with #Container, remove depth in path
PythonCaller_4
    NEW_ATTRIBUTES = parent_path buffer
    PYTHONSOURCE:
      import fme
      from fme import BaseTransformer
      import fmeobjects
      import re

      class FeatureProcessor(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def has_support_for(self, support_type: int):
              """This method is called by FME to determine if the PythonCaller supports Bulk mode,
              which allows for significant performance gains when processing large numbers of features.
              """
              return support_type == fmeobjects.FME_SUPPORT_FEATURE_TABLE_SHIM

          def input(self, feature: fmeobjects.FMEFeature):
              """This method is called for each feature which enters the PythonCaller."""
              path = feature.getAttribute('parent_path')

              # Loop as long as the path ends with the specific string
              while path.endswith("#Container"):
                  # Regex breakdown:
                  # \<pipe>      -> matches the literal pipe character
                  # [^<pipe>]+   -> matches one or more characters that are NOT a pipe
                  # #Container -> matches the literal string
                  # $       -> ensures we are only replacing the match at the very end
                  path = re.sub(r'\<pipe>[^<pipe>]+#Container$', '', path)

              feature.setAttribute('parent_path',path)
              self.pyoutput(feature, output_tag="PYOUTPUT")

          def close(self):
              """This method is called once all the FME Features have been processed from input()."""
              pass

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              self.pyoutput(feature, output_tag="<Rejected>")
    PYTHONSYMBOL = FeatureProcessor
    -> FeatureMerger_7 [REQUESTOR]
Note: Look for the UUID of the parent path
FeatureMerger_7
    ATTR_ACCUM_MODE = Merge Supplier
    ATTR_CONFLICT_RES_LOOKUP = REQUESTOR_IF_CONFLICT
    IGNORE_NULLS = No
    JOIN_KEYS = @Value(parent_path) @Value(path) AUTO @Value(_copynum) @Value(_copynum) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Junction_16
    UNMERGED_REQUESTOR -> Junction_16
Junction_16
    -> FeatureMerger_2 [REQUESTOR]
Note: add Relatics Operations, etc. to record
FeatureMerger_2
    ATTR_ACCUM_MODE = Merge Supplier
    ATTR_CONFLICT_RES_LOOKUP = REQUESTOR_IF_CONFLICT
    IGNORE_NULLS = No
    JOIN_KEYS = @Value(Operation) @Value(Operation) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Sorter
Note: ObjectInstances (UUID / ParentUUID)
Sorter
    SORT_PARM = depth NUMERIC ASCENDING
    SORTED -> Tester
    SORTED -> AttributeKeeper_7
Note: Tester [Tester] / Test Clauses: LogicLeft ValueOperatorRight Value@Value(foreignKey_parent)Attribute Has a ValueAND NOT@Value(childType)=http://www.w3.org/2000/01/rdf-schema#ContainerAdvanced: / Preserve Feature Order: Per Output Port
Tester
    BOOL_OP = AND
    TEST_CLAUSE:
      TEST foreignKey_parent ATTRIBUTE_HAS_A_VALUE ""
      TEST @Value(childType) NOT_= http://www.w3.org/2000/01/rdf-schema#Container
    TEST_MODE = TEST
    PASSED -> AttributeCreator_7
Note: Create Schema for Relatics Pre-Processing / Schema determines if it's foreignKey_object or foreignKey_space
AttributeCreator_7
    ATTR_TABLE:
      SET_TO attribute{0}.name (varchar(200)) = FME_CONDITIONAL:DEFAULT_VALUE'_FME_NO_OP_'BOOL_OP;OR;COMPOSITE_TEST;1;TEST @Value(type) = Object'foreignKey_object'BOOL_OP;OR;COMPOSITE_TEST;1;TEST @Value(type) = Space'foreignKey_space'FME_NUM_CONDITIONS3___
      SET_TO attribute{1}.name (varchar(5)) = child
      SET_TO attribute{2}.name (varchar(9)) = childName
      SET_TO attribute{3}.name (varchar(18)) = foreignKey_parent
      SET_TO attribute{4}.name (varchar(6)) = parent
      SET_TO attribute{5}.name (varchar(10)) = parentName
      SET_TO foreignKey_object (varchar(200)) = FME_CONDITIONAL:DEFAULT_VALUE'_FME_NO_OP_'BOOL_OP;OR;COMPOSITE_TEST;1;TEST @Value(type) = Object'@Value(foreignKey)'FME_NUM_CONDITIONS2___
      SET_TO foreignKey_space (varchar(200)) = FME_CONDITIONAL:DEFAULT_VALUE'_FME_NO_OP_'BOOL_OP;OR;COMPOSITE_TEST;1;TEST @Value(type) = Space'@Value(foreignKey)'FME_NUM_CONDITIONS2___
    -> AttributeRemover_6
AttributeRemover_6
    REMOVE_ATTRS = foreignKey,_copynum,depth,parent_path,path,type
    -> FeatureMerger_6 [REQUESTOR]
Note: foreign_key_object + child URI
AttributeKeeper_7
    CREATE_BULK_MODE_FEATURES = NO
    KEEP_ATTRS = child,foreignKey
    -> FeatureJoiner_5 [LEFT]
    -> FeatureJoiner_3 [LEFT]
Junction_3

Bookmark: Path + UUID as foreign_key_parent
AttributeKeeper_10
    CREATE_BULK_MODE_FEATURES = NO
    KEEP_ATTRS = foreignKey,_copynum,path
    -> AttributeRenamer_4
AttributeRenamer_4
    ATTR_TABLE = RENAME_SET_DEFAULT foreignKey > foreignKey_parent
    KEEP_RENAMED_ONLY = no
    MISSING_INPUT_ATTRS = REMOVE
    -> FeatureMerger_7 [SUPPLIER]

Bookmark: Prepare Queries to run for each concept
Note: Skip Containers
Tester_3
    BOOL_OP = OR
    TEST_CLAUSE = TEST @Value(childType) NOT_= http://www.w3.org/2000/01/rdf-schema#Container
    TEST_MODE = TEST
    PASSED -> AttributeKeeper_4
AttributeKeeper_4
    CREATE_BULK_MODE_FEATURES = NO
    KEEP_ATTRS = child,childName,childType,type
    -> FeatureJoiner_2 [LEFT]
Junction_10
    -> AttributeRemover_4
AttributeRemover_4
    LIST_ATTRS = _allmatch{}
    -> FeatureJoiner_2 [RIGHT]
Note: Attach each query to each object based on type
FeatureJoiner_2
    ATTR_CONFLICT_RES_LOOKUP = USE_LEFT
    GEOMETRY_HANDLING_LOOKUP = USE_LEFT
    JOIN_KEYS = type type AUTO
    JOIN_MODE = Inner
    ATTR_CONFLICT_RES = Prefer Left
    GEOMETRY_HANDLING = Prefer Left
    JOINED -> StringReplacer_2

Bookmark: Run queries for each concept
StringReplacer_2
    CASE = NO
    FIND_TEXT = {{uri}}
    NO_MATCH = _FME_NO_OP_
    REGEXP = NO
    REPLACE_TEXT = @Value(child)
    SRC_ATTRS = Query
    -> HTTPCaller_8
Note: SPARQL
HTTPCaller_8
    AUTH_METHOD_TYPE = NC
    AUTH_NAMED_CONNECTION = $(AUTH_NAMED_CONNECTION)
    CLIENT_CERTIFICATE_TYPE = NONE
    CONNECTION_TIMEOUT_LENGTH = 60
    CONTENT_TYPE_LOOKUP = application/sparql-query
    CUSTOM_HEADERS = Accept;application/json Accept-Charset;gzip,deflate,br
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    RATE_LIMIT_INTERVAL_IN_SECONDS = 60
    RATE_LIMIT_MAX_REQUESTS = $(RATE_LIMIT_MAX_REQUESTS)
    RATE_LIMIT_REQUEST_TIMING = BURST
    REDIRECT_AUTH = ORIGINAL_DOMAIN_ONLY
    RESPONSE_TYPE = Attribute
    RETRY_FAILED_TRANSFERS = CONNECTION 429
    RETRY_INITIAL_BACKOFF = $(RETRY_INITIAL_BACKOFF)
    RETRY_MAX_RETRIES = 3
    SPLIT_MULTIPART_DOWNLOADS = NO
    STATUS_CODE_ATTR = _http_status_code
    TARGET_ATTR = _response_body
    TARGET_ATTR_ENCODING = auto-detect
    TARGET_URL = @Value(QueryEndpoint)
    TRANSFER_TIMEOUT_LENGTH = 90
    UPLOAD_BODY = @Value(Query)
    UPLOAD_TYPE = STRING_UPLOAD
    USE_COOKIES = No
    VERIFY_SSL_CERTIFICATES = Yes
    AUTH_METHOD = Web Connection
    UPLOAD_CONTENT_TYPE = application/sparql-query
    -> Tester_7
Note: Result = empty
Tester_7
    BOOL_OP = OR
    TEST_CLAUSE = CASE_INSENSITIVE_TEST @Value(_response_body) CONTAINS "bindings" : [ ]
    TEST_MODE = TEST
    FAILED -> JSONExtractor

Bookmark: Schema for each query
JSONExtractor
    EXTRACT_QUERY_TABLE = vars json["head"]["vars"]
    JSON_DOCUMENT = @Value(_response_body)
    READ_FROM_FILE = NO
    EVALUATED -> StringSearcher_3
StringSearcher_3
    CASE = no
    MATCHED_PARTS_ATTR = _submatch
    MATCHED_RESULT_ATTR = _first_match
    MATCHES_ATTR = _allmatch
    REGEXP = "([^"]+)"
    STRING_TO_SEARCH = @Value(vars)
    MATCHED -> ListRenamer
ListRenamer
    LEAVE_ORIG = Yes
    LIST_ACTION = Rename
    LIST_COMPONENT_NAMES = _submatch{},attribute{},part,name
    LIST_NAME = _submatch{}.part
    -> AttributeRemover_2
AttributeRemover_2
    LIST_ATTRS = _allmatch{} _submatch{}
    REMOVE_ATTRS = _first_match,_http_status_code,vars
    -> ListElementCounter_2
ListElementCounter_2
    CNT_ATTR = _element_count
    LIST_NAME = attribute{}
    -> JSONFragmenter_8

Bookmark: Query records
JSONFragmenter_8
    EXPLODE_FORMAT = JSON
    EXTRACT_ATTR = Yes
    JSON_ATTR = _response_body
    JSON_QUERY = json["results"]["bindings"][*]
    READ_FROM_FILE = NO
    RECURSIVE = YES
    REJECT_EMPTY_LISTS = YES
    FRAGMENTS -> AttributeRemover_3
AttributeRemover_3
    REMOVE_ATTRS = _response_body
    -> BulkAttributeRenamer_2
Note: Remove suffix .value from <attribute>.value
BulkAttributeRenamer_2
    ATTRCHOICE_ACTION = NONPROTECTEDFME
    CASE_DISP = YES
    MODE_CHOICE = RENAME
    PATTERN_ACTION_DISP = REMOVESUFFIX
    REPLACE_STR = .value
    ATTRCHOICE = All Attributes
    -> TestFilter
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(QueryName) BEGINS_WITH GetRequirements",GetRequirements,"BOOL_OP,OR,COMPOSITE_TEST,""""""1"""""",TEST_CLAUSE,CASE_INSENSITIVE_TEST @Value(QueryName) BEGINS_WITH GetVerificationPlans",GetVerificationPlans,"BOOL_OP,OR,COMPOSITE_TEST,""""""1"""""",TEST_CLAUSE,CASE_INSENSITIVE_TEST @Value(QueryName) BEGINS_WITH GetVerification",GetVerification
    GetRequirements -> FeatureJoiner_5 [RIGHT]
    GetVerificationPlans -> AttributeExposer_2
    GetVerification -> AttributeExposer_3
    <UNFILTERED> -> FeatureJoiner_5 [RIGHT]

Bookmark: Join query results directly to objects
FeatureJoiner_5
    ATTR_CONFLICT_RES_LOOKUP = USE_LEFT
    GEOMETRY_HANDLING_LOOKUP = USE_LEFT
    JOIN_KEYS = child child AUTO
    JOIN_MODE = Inner
    ATTR_CONFLICT_RES = Prefer Left
    GEOMETRY_HANDLING = Prefer Left
    JOINED -> AttributeCreator_3
Note: Create Schema for Relatics Pre-Processing / Schema determines if it's foreignKey_object or foreignKey_space
AttributeCreator_3
    ATTR_TABLE:
      SET_TO attribute{@Value(_element_count)}.name (varchar(200)) = FME_CONDITIONAL:DEFAULT_VALUE'_FME_NO_OP_'BOOL_OP;OR;COMPOSITE_TEST;1;TEST @Value(type) = Object'foreignKey_object'BOOL_OP;OR;COMPOSITE_TEST;1;TEST @Value(type) = Space'foreignKey_space'FME_NUM_CONDITIONS3___
      SET_TO foreignKey_object (varchar(200)) = FME_CONDITIONAL:DEFAULT_VALUE'_FME_NO_OP_'BOOL_OP;OR;COMPOSITE_TEST;1;TEST @Value(type) = Object'@Value(foreignKey)'FME_NUM_CONDITIONS2___
      SET_TO foreignKey_space (varchar(200)) = FME_CONDITIONAL:DEFAULT_VALUE'_FME_NO_OP_'BOOL_OP;OR;COMPOSITE_TEST;1;TEST @Value(type) = Space'@Value(foreignKey)'FME_NUM_CONDITIONS2___
    -> AttributeRemover_5
AttributeRemover_5
    REMOVE_ATTRS = _element_count,foreignKey,json_index,json_type,Order,Query,QueryEndpoint,QueryName,type
    -> FeatureMerger_6 [REQUESTOR]

Bookmark: Verification needs FK to Verifcation Plan
AttributeExposer_2
    ATTR_TABLE = verificationPlanUri,
    -> FeatureJoiner_3 [RIGHT]
FeatureJoiner_3
    ATTR_CONFLICT_RES_LOOKUP = USE_LEFT
    GEOMETRY_HANDLING_LOOKUP = USE_LEFT
    JOIN_KEYS = child child AUTO
    JOIN_MODE = Inner
    ATTR_CONFLICT_RES = Prefer Left
    GEOMETRY_HANDLING = Prefer Left
    JOINED -> UniqueIdentifierGenerator
UniqueIdentifierGenerator
    UUID_ATTR = foreignKey_verificationPlan
    UUID_FORMAT = UUID_ONLY
    -> AttributeKeeper_8
    -> Junction_12
Note: VerificationPlan
Junction_12
    -> AttributeCreator_5
Note: Create Schema for Relatics Pre-Processing / Schema determines if it's foreignKey_object or foreignKey_space and foreignKey_verificationPlan
AttributeCreator_5
    ATTR_TABLE:
      SET_TO attribute{@Value(_element_count)}.name (varchar(200)) = FME_CONDITIONAL:DEFAULT_VALUE'_FME_NO_OP_'BOOL_OP;OR;COMPOSITE_TEST;1;TEST @Value(type) = Object'foreignKey_object'BOOL_OP;OR;COMPOSITE_TEST;1;TEST @Value(type) = Space'foreignKey_space'FME_NUM_CONDITIONS3___
      SET_TO attribute{@Evaluate(@Value(_element_count)+1)}.name (varchar(27)) = foreignKey_verificationPlan
      SET_TO foreignKey_object (varchar(200)) = FME_CONDITIONAL:DEFAULT_VALUE'_FME_NO_OP_'BOOL_OP;OR;COMPOSITE_TEST;1;TEST @Value(type) = Object'@Value(foreignKey)'FME_NUM_CONDITIONS2___
      SET_TO foreignKey_space (varchar(200)) = FME_CONDITIONAL:DEFAULT_VALUE'_FME_NO_OP_'BOOL_OP;OR;COMPOSITE_TEST;1;TEST @Value(type) = Space'@Value(foreignKey)'FME_NUM_CONDITIONS2___
    -> AttributeRemover_7
AttributeKeeper_8
    CREATE_BULK_MODE_FEATURES = NO
    KEEP_ATTRS = foreignKey_verificationPlan,verificationPlanUri
    -> FeatureJoiner_4 [LEFT]
Note: Requirements join with VerficationPlan
AttributeExposer_3
    ATTR_TABLE = verificationPlanUri,,verificationUri,,foreignKey_verificationResult,
    -> FeatureJoiner_4 [RIGHT]
FeatureJoiner_4
    ATTR_CONFLICT_RES_LOOKUP = USE_LEFT
    GEOMETRY_HANDLING_LOOKUP = USE_LEFT
    JOIN_KEYS = verificationPlanUri verificationPlanUri AUTO
    JOIN_MODE = Inner
    ATTR_CONFLICT_RES = Prefer Left
    GEOMETRY_HANDLING = Prefer Left
    JOINED -> Sorter_4
    <REJECTED> -> TestFilter_2
Note: Verification
Junction_13
    -> AttributeCreator_8
Note: Create Schema for Relatics Pre-Processing / Schema determines if it's foreignKey_object or foreignKey_space and foreignKey_verificationResult
AttributeCreator_8
    ATTR_TABLE:
      SET_TO attribute{@Value(_element_count)}.name (varchar(27)) = foreignKey_verificationPlan
      SET_TO attribute{@Evaluate(@Value(_element_count)+1)}.name (varchar(27)) = foreignKey_verificationResult
      SET_TO _nvt_attribute{@Evaluate(@Value(_element_count)+1)}.name (varchar(200)) = FME_CONDITIONAL:DEFAULT_VALUE'_FME_NO_OP_'BOOL_OP;OR;COMPOSITE_TEST;1;TEST @Value(type) = Object'foreignKey_object'BOOL_OP;OR;COMPOSITE_TEST;1;TEST @Value(type) = Space'foreignKey_space'FME_NUM_CONDITIONS3___
    -> AttributeRemover_7
AttributeRemover_7
    REMOVE_ATTRS = _element_count,foreignKey,json_index,json_type,Order,Query,QueryEndpoint,QueryName,type
    -> FeatureMerger_6 [REQUESTOR]
TestFilter_2
    DEFAULT_VALUE = <UNFILTERED>
    PASSED_TEST_GROUP_OUTPUT = FIRST
    TEST_LIST = "BOOL_OP,OR,COMPOSITE_TEST,""""""1"""""",TEST_CLAUSE,TEST @Value(fme_rejection_code) = MISSING_LEFT_KEY",MISSING_LEFT_KEY,"BOOL_OP,OR,COMPOSITE_TEST,""""""1"""""",TEST_CLAUSE,TEST @Value(fme_rejection_code) = MISSING_RIGHT_KEY",MISSING_RIGHT_KEY
    MISSING_LEFT_KEY -> Terminator_3
    MISSING_RIGHT_KEY -> Terminator_4
    <UNFILTERED> -> Terminator_5
Terminator_3
    MESSAGE = Translation Terminated: @Value(fme_rejection_code) The VerificationPlan Query didn't have a value for 'verificationPlanUri'
Terminator_4
    MESSAGE = Translation Terminated: @Value(fme_rejection_code) The Verification Query didn't have a value for 'verificationPlanUri'
Terminator_5
    MESSAGE = Translation Terminated: The Join of Verification Plan to Verifcation gave an unexpected error: @Value(fme_rejection_message)

Bookmark: UUID For each VerificationUri per Verification Plan
Sorter_4
    SORT_PARM = foreignKey_verificationPlan NATURAL ASCENDING verificationUri NATURAL ASCENDING
    SORTED -> AttributeCreator_11
Note: UUID foreignKey_verificationResult per change in VerificationURI per foreignKey_verificationPlan
AttributeCreator_11
    ATTR_TABLE = SET_TO foreignKey_verificationResult (varchar(200)) = FME_CONDITIONAL:DEFAULT_VALUE'@Value(feature[-1].foreignKey_verificationResult)'BOOL_OP;OR;COMPOSITE_TEST;1;TEST @Value(foreignKey_verificationPlan) != @Value(feature[-1].foreignKey_verificationPlan)'@UUID()'BOOL_OP;OR;COMPOSITE_TEST;1;TEST @Value(verificationUri) != @Value(feature[-1].verificationUri)'@UUID()'FME_NUM_CONDITIONS3___
    NUM_PRIOR_FEATURES = 1
    NUM_SUBSEQUENT_FEATURES = 0
    -> Junction_13

Bookmark: Generic Imports
DuplicateFilter_5
    INPUT_ORDERED_CHOICE_LOOKUP = NO
    KEYATTR = Query QueryName
    INPUT_ORDERED_CHOICE = No
    UNIQUE -> HTTPCaller_4
HTTPCaller_4
    AUTH_METHOD_TYPE = NC
    AUTH_NAMED_CONNECTION = $(AUTH_NAMED_CONNECTION)
    CLIENT_CERTIFICATE_TYPE = NONE
    CONNECTION_TIMEOUT_LENGTH = 60
    CONTENT_TYPE_LOOKUP = application/sparql-query
    CUSTOM_HEADERS = Accept;application/json Accept-Charset;gzip,deflate,br
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    RATE_LIMIT_INTERVAL_IN_SECONDS = 60
    RATE_LIMIT_MAX_REQUESTS = $(RATE_LIMIT_MAX_REQUESTS)
    RATE_LIMIT_REQUEST_TIMING = BURST
    REDIRECT_AUTH = ORIGINAL_DOMAIN_ONLY
    RESPONSE_TYPE = Attribute
    RETRY_FAILED_TRANSFERS = CONNECTION 429
    RETRY_INITIAL_BACKOFF = $(RETRY_INITIAL_BACKOFF)
    RETRY_MAX_RETRIES = 3
    SPLIT_MULTIPART_DOWNLOADS = NO
    STATUS_CODE_ATTR = _http_status_code
    TARGET_ATTR = _response_body
    TARGET_ATTR_ENCODING = auto-detect
    TARGET_URL = @Value(QueryEndpoint)
    TRANSFER_TIMEOUT_LENGTH = 90
    UPLOAD_BODY = @Value(Query)
    UPLOAD_TYPE = STRING_UPLOAD
    USE_COOKIES = No
    VERIFY_SSL_CERTIFICATES = Yes
    AUTH_METHOD = Web Connection
    UPLOAD_CONTENT_TYPE = application/sparql-query
    -> AttributeKeeper_12
AttributeKeeper_12
    CREATE_BULK_MODE_FEATURES = NO
    KEEP_ATTRS = _response_body,Entrycode,Filename,Operation,Order,QueryName
    -> JSONExtractor_3
JSONExtractor_3
    EXTRACT_QUERY_TABLE = vars json["head"]["vars"]
    JSON_DOCUMENT = @Value(_response_body)
    READ_FROM_FILE = NO
    EVALUATED -> StringSearcher_7
    <REJECTED> -> Logger_4
Logger_4
    LOG_FEATURE = NONE
    MAXFEATS = 20
    MESSAGE:
      Query @Value(Order): @Value(QueryName) failed to produce a result:

      @Value(_response_body)
    SEVERITY = ERROR
Note: Headers
StringSearcher_7
    CASE = no
    MATCHED_PARTS_ATTR = attribute
    MATCHED_RESULT_ATTR = _first_match
    MATCHES_ATTR = _all_match
    REGEXP = "([^"]+)"
    STRING_TO_SEARCH = @Value(vars)
    MATCHED -> JSONFragmenter_3
Note: Bindings
JSONFragmenter_3
    EXPLODE_FORMAT = JSON
    EXTRACT_ATTR = Yes
    JSON_ATTR = _response_body
    JSON_QUERY = json[*]["bindings"][*]
    READ_FROM_FILE = NO
    RECURSIVE = YES
    REJECT_EMPTY_LISTS = YES
    FRAGMENTS -> AttributeRemover_9
AttributeRemover_9
    LIST_ATTRS = _all_match{} attribute{}.startIndex
    REMOVE_ATTRS = _first_match,_response_body,json_index,json_type,vars
    -> ListRenamer_3
ListRenamer_3
    LEAVE_ORIG = No
    LIST_ACTION = Rename
    LIST_COMPONENT_NAMES = attribute{},attribute{},part,name
    LIST_NAME = attribute{}.part
    -> BulkAttributeRenamer_4
BulkAttributeRenamer_4
    ATTRCHOICE_ACTION = NONPROTECTEDFME
    CASE_DISP = YES
    MODE_CHOICE = RENAME
    PATTERN_ACTION_DISP = REMOVESUFFIX
    REPLACE_STR = .value
    ATTRCHOICE = All Attributes
    -> Junction_14
Note: FeatureMerger_6 : Supplier
Junction_14
    -> Junction_15

Bookmark: Publication
DuplicateFilter_4
    INPUT_ORDERED_CHOICE_LOOKUP = NO
    KEYATTR = Query QueryName
    INPUT_ORDERED_CHOICE = No
    UNIQUE -> HTTPCaller_2
HTTPCaller_2
    AUTH_METHOD_TYPE = NC
    AUTH_NAMED_CONNECTION = $(AUTH_NAMED_CONNECTION)
    CLIENT_CERTIFICATE_TYPE = NONE
    CONNECTION_TIMEOUT_LENGTH = 60
    CONTENT_TYPE_LOOKUP = application/sparql-query
    CUSTOM_HEADERS = Accept;application/json Accept-Charset;gzip,deflate,br
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    RATE_LIMIT_INTERVAL_IN_SECONDS = 60
    RATE_LIMIT_MAX_REQUESTS = $(RATE_LIMIT_MAX_REQUESTS)
    RATE_LIMIT_REQUEST_TIMING = BURST
    REDIRECT_AUTH = ORIGINAL_DOMAIN_ONLY
    RESPONSE_TYPE = Attribute
    RETRY_FAILED_TRANSFERS = CONNECTION 429
    RETRY_INITIAL_BACKOFF = $(RETRY_INITIAL_BACKOFF)
    RETRY_MAX_RETRIES = 3
    SPLIT_MULTIPART_DOWNLOADS = NO
    STATUS_CODE_ATTR = _http_status_code
    TARGET_ATTR = _response_body
    TARGET_ATTR_ENCODING = auto-detect
    TARGET_URL = @Value(QueryEndpoint)
    TRANSFER_TIMEOUT_LENGTH = 90
    UPLOAD_BODY = @Value(Query)
    UPLOAD_TYPE = STRING_UPLOAD
    USE_COOKIES = No
    VERIFY_SSL_CERTIFICATES = Yes
    AUTH_METHOD = Web Connection
    UPLOAD_CONTENT_TYPE = application/sparql-query
    -> AttributeKeeper_11
AttributeKeeper_11
    CREATE_BULK_MODE_FEATURES = NO
    KEEP_ATTRS = _response_body
    -> JSONExtractor_2
JSONExtractor_2
    EXTRACT_QUERY_TABLE = vars json["head"]["vars"]
    JSON_DOCUMENT = @Value(_response_body)
    READ_FROM_FILE = NO
    EVALUATED -> StringSearcher_4
    <REJECTED> -> Terminator
Terminator
    MESSAGE:
      Translation Terminated: Publication Query didn't return a result

      @Value(_response_body)
Note: Headers
StringSearcher_4
    CASE = no
    MATCHED_PARTS_ATTR = publicationHeaders
    MATCHED_RESULT_ATTR = _first_match
    MATCHES_ATTR = _all_match
    REGEXP = "([^"]+)"
    STRING_TO_SEARCH = @Value(vars)
    MATCHED -> JSONFragmenter_2
Note: Bindings
JSONFragmenter_2
    EXPLODE_FORMAT = JSON
    EXTRACT_ATTR = Yes
    JSON_ATTR = _response_body
    JSON_QUERY = json[*]["bindings"][*]
    READ_FROM_FILE = NO
    RECURSIVE = YES
    REJECT_EMPTY_LISTS = YES
    FRAGMENTS -> Sampler_2
Sampler_2
    MODE = ORIGINAL
    RATE = 1
    SAMPLE_TYPE_MULTIPLIER = -1
    SAMPLE_MODE = No
    SAMPLE_TYPE_LONG = First N Features
    SAMPLED -> AttributeRemover_8
AttributeRemover_8
    LIST_ATTRS = _all_match{} publicationHeaders{}.startIndex
    REMOVE_ATTRS = _first_match,_response_body,json_index,json_type,vars
    -> ListRenamer_2
ListRenamer_2
    LEAVE_ORIG = No
    LIST_ACTION = Rename
    LIST_COMPONENT_NAMES = publicationHeaders{},publicationHeaders{},part,name
    LIST_NAME = publicationHeaders{}.part
    -> BulkAttributeRenamer_3
BulkAttributeRenamer_3
    ATTRCHOICE_ACTION = NONPROTECTEDFME
    CASE_DISP = YES
    MODE_CHOICE = RENAME
    PATTERN_ACTION_DISP = REMOVESUFFIX
    REPLACE_STR = .value
    ATTRCHOICE = All Attributes
    -> PythonCaller_2
Note: Loop through publicationHeaders{}.name Remove & and < from attributes values if it has a value
PythonCaller_2
    PYTHONSOURCE:
      import fme
      import fmeobjects


      class FeatureProcessor(object):
          """Template Class Interface:
          When using this class, make sure its name is set as the value of the 'Class
          to Process Features' transformer parameter.
          """

          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              publicationHeaders = feature.getAttribute('publicationHeaders{}.name')
              for h in publicationHeaders:
                  ### bugfix: string() makes sure that an attribute is always
                  ### replaceable, in case attribute contains only numbers
                  att = feature.getAttribute(h)
                  if att is None:
                      pass
                  else:
                      att = str(att)
                      new1 = att.replace('&','&amp;')
                      new2 = new1.replace('<','&lt;')
                      feature.setAttribute(h,new2)

              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> Junction_6
Note: FeatureMerger_6 : Supplier
Junction_6
    -> Junction_11

Bookmark: Add Publication
Note: Publication: PythonCaller_2
Junction_11
    -> FeatureMerger_6 [SUPPLIER]
FeatureMerger_6
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> PythonCaller

Bookmark: 3.3 Relatics Import
Note: Base64 Encoded Import rows
TextEncoder_2
    DEST_ATTR = _encoded
    ENCODING_TYPE = BASE64_ENCODE
    STRING_TO_ENCODE = @Value(RelaticsDataXML)
    -> TextEncoder
Note: Operation as XML (replace & )
TextEncoder
    DEST_ATTR = Operation
    ENCODING_TYPE = XML_ENCODE
    STRING_TO_ENCODE = @Value(Operation)
    -> AttributeCreator_4
Note: SoapXML
AttributeCreator_4
    ATTR_TABLE:
      SET_TO soapXML = <SOAP-ENV:Envelope xmlns:SOAP-ENV="http://www.w3.org/2003/05/soap-envelope" xmlns:xsi="http://www.w3.org/2001/XMLSchema-instance" xmlns:xsd="http://www.w3.org/2001/XMLSchema">
          <SOAP-ENV:Body>
            <Import xmlns="http://www.relatics.com/">
              <Operation>@Value(Operation)</Operation>
              <Identification>
                <Identification>
                  <Workspace>$(RelaticsWorkspace)</Workspace>
                </Identification>
              </Identification>
              <Authentication>
                <Authentication>
                  <Entrycode>@Value(Entrycode)</Entrycode>
                </Authentication>
              </Authentication>
              <Filename>@Value(Filename)</Filename>
              <Data>
              @Value(_encoded)
              </Data>
            </Import>
          </SOAP-ENV:Body>
        </SOAP-ENV:Envelope>
    -> HTTPCaller_3
HTTPCaller_3
    CLIENT_CERTIFICATE_TYPE = NONE
    CONNECTION_TIMEOUT_LENGTH = 3600
    CONTENT_TYPE_LOOKUP = application/soap+xml
    ERROR_ATTR = _error
    FOLLOW_REDIRECTS = FOLLOW_WITH_GET
    HTTP_METHOD = POST
    MAX_HTTP_VERSION = HTTP_2
    MAX_TRANSFERS_IN_PROGRESS = 1
    MINIMUM_ENCRYPTION_LEVEL = OS_DEFAULT
    REDIRECT_AUTH = ORIGINAL_DOMAIN_ONLY
    RESPONSE_HEADER_LIST_ATTR = _response_headers
    RESPONSE_TYPE = Attribute
    SPLIT_MULTIPART_DOWNLOADS = NO
    STATUS_CODE_ATTR = _http_status_code
    TARGET_ATTR = _response_body
    TARGET_ATTR_ENCODING = auto-detect
    TARGET_URL = $(TARGET_URL)
    TRANSFER_TIMEOUT_LENGTH = 0
    UPLOAD_BODY = @Value(soapXML)
    UPLOAD_TYPE = STRING_UPLOAD
    USE_COOKIES = No
    VERIFY_SSL_CERTIFICATES = Yes
    UPLOAD_CONTENT_TYPE = SOAP XML (application/soap+xml)
    -> Tester_9
    -> XMLFormatter
    <REJECTED> -> AttributeRemover
Tester_9
    BOOL_OP = OR
    TEST_CLAUSE = TEST $(REPORT_YESNO) = Yes
    TEST_MODE = TEST
    PASSED -> StringSearcher
StringSearcher
    CASE = no
    MATCHES_ATTR = _matches
    PRESERVE_FEATURE_ORDER_LOOKUP = PER_OUTPUT_PORT
    REGEXP = Message Time="([\d:]+)" Result="(Progress|Error)">([^<]+)</Message>
    STRING_TO_SEARCH = @Value(_response_body)
    MATCHED -> AttributeKeeper_3
AttributeKeeper_3
    CREATE_BULK_MODE_FEATURES = NO
    KEEP_ATTRS = Filename,Operation
    KEEP_LIST = _matches{}.match
    -> ListExploder
ListExploder
    ATTR_CONFLICT_RES_LOOKUP = INCOMING_IF_CONFLICT
    INDEX_ATTR = _element_index
    LIST_ATTR = _matches{}
    ATTR_ACCUM_MODE = Merge List Attributes
    ATTR_CONFLICT_RES = Use List Attribute Values
    ELEMENTS -> Tester_8
Tester_8
    BOOL_OP = OR
    TEST_CLAUSE = CASE_SENSITIVE_TEST @Value(match) NOT_CONTAINS Processing row
    TEST_MODE = CASE_SENSITIVE_TEST
    PASSED -> StringReplacer
StringReplacer
    CASE = NO
    FIND_TEXT = </Message>
    NO_MATCH = _FME_NO_OP_
    REGEXP = NO
    SRC_ATTRS = match
    -> HTMLReportGenerator
HTMLReportGenerator
    CONTENT_LIST = HEADER TABLE
    GROUP_BY = Filename Operation
    PAGE_CONFIG:
      HEADER{{TEXT;Relatics Import: @Value(Operation)
      Filename: @Value(Filename);HEADER;$(HEADER);HEADER_ID;;ALIGNMENT;LEFT;COLOR;0,0,0;FME_CONTROLLER_QUERY_FILE;transformers/dependencies/html5/Header.fme;FME_CONTROLLER_CHOICE;Header}}TABLE{{STYLE;DEFAULT;TABLE;match|Message;FME_CONTROLLER_QUERY_FILE;transformers/dependencies/html5/Table.fme;FME_CONTROLLER_CHOICE;Table}}
    -> StringSearcher_2
StringSearcher_2
    CASE = no
    MATCHED_PARTS_ATTR = submatch
    PRESERVE_FEATURE_ORDER_LOOKUP = PER_OUTPUT_PORT
    REGEXP = (.+)-(\d+)\.xml
    STRING_TO_SEARCH = @Value(Filename)
    MATCHED -> Sorter_2
Sorter_2
    SORT_PARM = submatch{0}.part ALPHA ASCENDING submatch{1}.part NUMERIC ASCENDING
    SORTED -> HTMLLayouter_2
HTMLLayouter_2
    DIV_STYLE = NONE
    GROUP_BY = Operation
    LAYOUT = VERTICAL
    TITLE = @Value(Operation)
    -> HTML (writer HTML_1)
HTML (writer HTML_1)
    attributes: html_content buffer
AttributeRemover
    LIST_ATTRS = _feature_types{}
    REMOVE_ATTRS = RelaticsDataXML,_dataset,_dirname,_dirpath,_encoded,_extension,_file_contents
    -> Logger
Logger
    LOG_FEATURE = NONE
    MAXFEATS = 20
    MESSAGE:
      Relatics Response indicated an error on step: @Value(Operation)
      Statuscode: @Value(_http_status_code) @Value(_error)
      Response:
      @Value(_response_body)
    SEVERITY = ERROR
    LOGGED -> Terminator_2
Terminator_2
    MESSAGE = Translation Terminated: Relatics returned an error
XMLFormatter [off]
    COLLAPSE_EMPTY_ELEMENT = No
    FORMAT_MODE = PRETTY_PRINT
    INDENT_SIZE = 1
    LIST_NAME = _xml_error
    NAMESPACE_CLEANUP = No
    OUTPUT_ENCODING = utf-8
    PARSER_CHOICE = LIBXML2
    REMOVE_ALL_COMMENT = No
    REMOVE_DTD = No
    REMOVE_EMPTY_ELEMENT = No
    REMOVE_XML_HEADER = no
    REPLACE_TABS_WITH_SPACES = no
    SCHEMALOC_CLEANUP = No
    TEXT_INDENT = no
    WHITESPACE_HANDLING = Preserve all whitespace
    XML_ATTR_TEXT = _response_body
    XML_INPUT_TYPE = Attribute Specifying XML Text
    XML_OUTPUT_ATTR = _xml_output
    XML_OUTPUT_TYPE = Attribute
    FORMATTING_CHOICE = Pretty-Print XML

Bookmark: Remove Containers from path
StringReplacer_4 [off]
    CASE = NO
    FIND_TEXT = [^<pipe>]+#Container
    NO_MATCH = _FME_NO_OP_
    REGEXP = YES
    SRC_ATTRS = path
    TEST_STRING = http://data.tennet.eu/id/2ef0117e-6a10-f011-b6c1-001dd8d702b3 Standaard fundaties 150kV http://www.w3.org/2000/01/rdf-schema#Container|http://data.tennet.eu/id/2650af65-7e4d-ef11-b6b2-001dd8d702ae stationsfundering - fundatie veld https://w3id.org/nen2660/def#RealObject
    -> StringReplacer_5 [off]
StringReplacer_5 [off]
    CASE = NO
    FIND_TEXT = \<pipe>+
    NO_MATCH = _FME_NO_OP_
    REGEXP = YES
    REPLACE_TEXT = <pipe>
    SRC_ATTRS = path
    -> AttributeTrimmer [off]
AttributeTrimmer [off]
    SRC_ATTRS = path
    TRIM_CHARS = <pipe>
    TRIM_TO_NONE = Yes
    TRIM_TYPE = BOTH

FME custom transformer BatchGrouper

Parameters:
- GROUP_SIZE = 100   # Group/Batch Size
- VAL_ATTR =   # ALLOW_NEW New Group Attribute
- DOMAIN = counter   # GroupBy

Input (input)
    -> Counter
Output (output)

Bookmark: Group/Batch Features Based on Size
Counter
    CNT_ATTR = _groupByCount
    DOMAIN = $(DOMAIN)
    SCOPE = Local
    START = 0
    SCOPEVAR = Local
    -> ExpressionEvaluator
ExpressionEvaluator
    ACTION = Create New Attribute
    EXPRESSION = @floor(@Value(_groupByCount)/$(GROUP_SIZE))
    VAL_ATTR = $(VAL_ATTR)
    -> AttributeRemover
AttributeRemover
    REMOVE_ATTRS = _groupByCount
    -> Output (output)

FME custom transformer GetSOVChildren

Parameters:
- TARGET_URL = https://hub.laces.tech/tennet/gfo-nl/sov/b7_brp_productline/versions/v_5/sparql   # Request URL
- _SELECTEDGROUP = @Value(_SelectedGroup)   # Selectedgroup
- _QUERY = @Value(_query)   # Query
- _PATH = @Value(_path)   # Path
- _LEVEL = @Value(_level)   # Level
- AUTH_NAMED_CONNECTION =   # EXCLUDE_SERVICES:"Amazon Web Services","HDFS Insecure Client","HDFS Delegation Token","HDFS Kerberos" Web Connection
- RETRY_INITIAL_BACKOFF = 500   # Initial Backoff Time (msec)
- RATE_LIMIT_MAX_REQUESTS =   # Maximum Requests per Interval

Input (input)
    -> AttributeCopier
AttributeCopier
    ATTR_TABLE = COPY _query > _specific_query
    MISSING_INPUT_ATTRS = REMOVE
    -> StringReplacer
StringReplacer
    CASE = NO
    FIND_TEXT = {{uri}}
    NO_MATCH = _FME_NO_OP_
    REGEXP = NO
    REPLACE_TEXT = @Value(_SelectedGroup)
    SRC_ATTRS = _specific_query
    -> AttributeCreator_2
AttributeRemover
    REMOVE_ATTRS = _http_status_code,_response_body,json_index,json_type
    -> DuplicateFilter
DuplicateFilter
    INPUT_ORDERED_CHOICE_LOOKUP = NO
    KEYATTR = child
    INPUT_ORDERED_CHOICE = No
    UNIQUE -> Input (output)
    UNIQUE -> AttributeRemover_2
    DUPLICATE -> AttributeRemover_3
AttributeRemover_2
    REMOVE_ATTRS = _level,_query,_SelectedGroup,_specific_query
    -> UniqueChild (output)
UniqueChild (output)
Input (output)
AttributeRemover_3
    REMOVE_ATTRS = _level,_query,_SelectedGroup,_specific_query
    -> DuplicateChild (output)
DuplicateChild (output)
Junction
    -> <Rejected> (output)
<Rejected> (output)

Bookmark: Get Children
AttributeCreator_2
    ATTR_TABLE = SET_TO _level (real64) = @Evaluate(@Value(_level)+1)
    -> HTTPCaller_2
Note: Get Child
HTTPCaller_2
    AUTH_METHOD_TYPE = NC
    AUTH_NAMED_CONNECTION = $(AUTH_NAMED_CONNECTION)
    CLIENT_CERTIFICATE_TYPE = NONE
    CONNECTION_TIMEOUT_LENGTH = 60
    CONTENT_TYPE_LOOKUP = application/sparql-query
    CUSTOM_HEADERS = Accept;application/json Accept-Charset;gzip,deflate,br
    ERROR_ATTR = _error
    FOLLOW_REDIRECTS = FOLLOW_WITH_GET
    HTTP_METHOD = POST
    MAX_HTTP_VERSION = HTTP_2
    MAX_TRANSFERS_IN_PROGRESS = 1
    MINIMUM_ENCRYPTION_LEVEL = OS_DEFAULT
    RATE_LIMIT_INTERVAL_IN_SECONDS = 60
    RATE_LIMIT_MAX_REQUESTS = $(RATE_LIMIT_MAX_REQUESTS)
    RATE_LIMIT_REQUEST_TIMING = BURST
    REDIRECT_AUTH = ORIGINAL_DOMAIN_ONLY
    RESPONSE_TYPE = Attribute
    RETRY_FAILED_TRANSFERS = CONNECTION 429
    RETRY_INITIAL_BACKOFF = $(RETRY_INITIAL_BACKOFF)
    RETRY_MAX_RETRIES = 3
    SPLIT_MULTIPART_DOWNLOADS = NO
    STATUS_CODE_ATTR = _http_status_code
    TARGET_ATTR = _response_body
    TARGET_ATTR_ENCODING = auto-detect
    TARGET_URL = $(TARGET_URL)
    TRANSFER_TIMEOUT_LENGTH = 90
    UPLOAD_BODY = @Value(_specific_query)
    UPLOAD_TYPE = STRING_UPLOAD
    USE_COOKIES = No
    VERIFY_SSL_CERTIFICATES = Yes
    AUTH_METHOD = Web Connection
    UPLOAD_CONTENT_TYPE = application/sparql-query
    -> Junction_3
    <REJECTED> -> Junction
Note: Decomposition
Junction_3
    -> Tester
Tester
    BOOL_OP = OR
    TEST_CLAUSE = CASE_INSENSITIVE_TEST @Value(_response_body) CONTAINS "bindings" : [ ]
    TEST_MODE = CASE_INSENSITIVE_TEST
    FAILED -> JSONFragmenter_2
JSONFragmenter_2
    EXPLODE_FORMAT = JSON
    EXTRACT_ATTR = Yes
    JSON_ATTR = _response_body
    JSON_QUERY = json["results"]["bindings"][*]
    READ_FROM_FILE = NO
    RECURSIVE = YES
    REJECT_EMPTY_LISTS = YES
    FRAGMENTS -> AttributeExposer_3
    <REJECTED> -> Junction
AttributeExposer_3
    ATTR_TABLE = child.value,varchar(61),childName.value,varchar(50),childType.value,varchar(39),parent.value,varchar(61),parentName.value,varchar(26),parentType.value,varchar(39)
    -> BulkAttributeRenamer_2
BulkAttributeRenamer_2
    ATTRCHOICE_ACTION = SELECTED
    ATTRLIST = child.value childName.value childType.value parent.value parentName.value parentType.value
    CASE_DISP = YES
    MODE_CHOICE = RENAME
    PATTERN_ACTION_DISP = REMOVESUFFIX
    REPLACE_STR = .value
    ATTRCHOICE = Selected Attributes
    -> AttributeCreator_5
AttributeCreator_5
    ATTR_TABLE:
      SET_TO _SelectedGroup (buffer) = @Value(child)
      SET_TO _path (varchar(200)) = @Value(_path)<pipe>@Value(childName) <@Value(child)>
    -> AttributeRemover
