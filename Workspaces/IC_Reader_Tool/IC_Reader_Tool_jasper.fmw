FME workspace IC_Reader_Tool_jasper.fmw

Parameters:
- RUN_UUID:   # UUID
      import fme
      from uuid import uuid4
      
      return str(uuid4())
- InformationContainer = C:\Users\JasperKlingenAvineon\Downloads\IC_B6.0_ContractExample.zip   # IC Path
- SPARQL_CONFIG = C:\Users\JasperKlingenAvineon\OneDrive - Avineon-Tensing\Documents\Tennet Opdracht Oscar\April 2026\IC_Reader_Tool_Config_v4.xlsx   # Excel with SPARQL-queries
- SYSTEM =   # System Parameters
- AUTH_USERNAME = ab402675-b25b-49f1-bbcb-7ef35566d993   # HTTP Authentication Username
- AUTH_PASSWORD =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   # HTTP Authentication Password
- LACES_REPO = 1fe0104d-14c0-461e-9234-af1b8bf03b7a   # Laces Repository
- LACES_BASE_URL = https://hub.laces.tech   # Laces Base URL
- OUT_HTML = C:\Users\OscarWillemsAvineon-\OneDrive - Tensing\Documents\Consultancy\TenneT\Dashboard\ICReport.html   # Destination Html File

Readers:
- XLSXR_1: XLSXR from $(SPARQL_CONFIG)

Writers:
- HTML_1: HTML to $(OUT_HTML)

AttributeCreator
    ATTR_TABLE = SET_TO Order (uint8) = 0
    -> FilenamePartExtractor
Config (reader XLSXR_1)
    attributes: Order number(2,0), Query char(590), QueryName char(49), Explanation char(85), Type char(5)
    -> FeatureMerger [REQUESTOR]

Bookmark: TTL to hub.laces
Creator
    GEOMTYPE = Geometry Object
    NUM = 1
    CREATED -> AC_PathWindows
AC_PathWindows: AttributeCreator
    ATTR_TABLE = SET_TO path_windows (varchar(200)) = $(InformationContainer)
    -> PythonCaller
Note: Combine Graphs
PythonCaller
    NEW_ATTRIBUTES = graph buffer
    PYTHONSOURCE:
      import os
      import zipfile
      import tempfile
      from pathlib import Path
      import fme
      from fme import BaseTransformer
      import fmeobjects
      from rdflib import Graph

      class FeatureProcessor(BaseTransformer):

          def __init__(self):
              self.feature_list = []

          def has_support_for(self, support_type: int):
              return support_type == fmeobjects.FME_SUPPORT_FEATURE_TABLE_SHIM

          def input(self, feature: fmeobjects.FMEFeature):
              self.feature_list.append(feature.getAttribute('path_windows'))

          def close(self):
              pass

          def process_group(self):
              graph = Graph()
              newFeature = fmeobjects.FMEFeature()
              for path in self.feature_list:
                  ext = os.path.splitext(path)[1].lower()

                  if ext == '.ttl':
                      with open(path, 'r', encoding='utf-8') as f:
                          g = Graph()
                          g.parse(data=f.read(), format="turtle")
                          graph = graph + g

                  elif ext == '.zip':
                      temp_dir = tempfile.mkdtemp()
                      with zipfile.ZipFile(path, 'r') as zf:
                          zf.extractall(temp_dir)
                      for root, dirs, files in os.walk(temp_dir):
                          for fname in files:
                              if fname.lower().endswith('.ttl'):
                                  ttl_path = os.path.join(root, fname)
                                  with open(ttl_path, 'r', encoding='utf-8') as f:
                                      g = Graph()
                                      g.parse(data=f.read(), format="turtle")
                                      graph = graph + g

              newFeature.setAttribute("graph", graph.serialize(format="turtle"))
              self.pyoutput(newFeature)

          def reject_feature(self, feature, code, message):
              feature.setAttribute("fme_rejection_code", code)
              feature.setAttribute("fme_rejection_message", message)
              self.pyoutput(feature, output_tag="<Rejected>")
    PYTHONSYMBOL = FeatureProcessor
    -> TempPathnameCreator
TempPathnameCreator
    PATHNAME_ATTR = _pathname
    -> AttributeCreator_25
Note: Publication Metadata
AttributeCreator_25
    ATTR_TABLE:
      SET_TO _uuid = $(RUN_UUID)
      SET_TO metadataJSON = {
            "publicationUri": "@Value(_uuid)",
            "name": "@Value(_uuid)",
            "description": "Dataset for statistics (@Value(_uuid))",
            "owner": "TenneT",
            "publisher": "FME",
            "versioningMode": "NONE",
            "versionLabel": "",
            "schemaURIs": [ ]
        }
      SET_TO file_path = @Value(_pathname)\@Value(_uuid).ttl
    -> AttributeFileWriter
AttributeFileWriter
    CHAR_ENCODING = utf-8
    FILE_NAME = @Value(file_path)
    OVERWRITE_FILE_LOOKUP = DestWriteSrcRead
    SOURCE_ATTR = graph
    OVERWRITE_FILE = Overwrite file
    -> HTTPCaller_5
Note: Upload to Laces
HTTPCaller_5
    AUTH_METHOD_TYPE = BASIC
    AUTH_PASSWORD = $(AUTH_PASSWORD)
    AUTH_USERNAME = $(AUTH_USERNAME)
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    MULTIPARTS = metadata StringUpload SOURCE_EXPRESSION;@Value(metadataJSON);MIME_TYPE;application/json;FME_CONTROLLER_QUERY_FILE;transformers/dependencies/http/StringUpload.fme;FME_CONTROLLER_CHOICE;StringUpload content FileUpload SOURCE_FILE;@Value(file_path);MIME_TYPE;application/octet-stream;FME_CONTROLLER_QUERY_FILE;transformers/dependencies/http/FileUpload.fme;FME_CONTROLLER_CHOICE;FileUpload
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(LACES_BASE_URL)/api/v3/repositories/$(LACES_REPO)/publications
    TRANSFER_TIMEOUT_LENGTH = 90
    UPLOAD_TYPE = Multipart / Form Data
    USE_COOKIES = No
    VERIFY_SSL_CERTIFICATES = Yes
    AUTH_METHOD = Basic
    -> JSONExtractor
JSONExtractor
    EXTRACT_QUERY_TABLE = publication_id json["id"] uri json["uri"]
    JSON_DOCUMENT = @Value(_response_body)
    READ_FROM_FILE = NO
    EVALUATED -> AttributeRenamer_4
AttributeRenamer_4
    ATTR_TABLE:
      RENAME_SET_DEFAULT uri > LacesUri
      RENAME_SET_DEFAULT publication_id > LacesPublication
    KEEP_RENAMED_ONLY = no
    MISSING_INPUT_ATTRS = REMOVE
    -> AttributeKeeper_4
AttributeKeeper_4
    CREATE_BULK_MODE_FEATURES = NO
    KEEP_ATTRS = LacesPublication,LacesUri
    -> FeatureMerger [SUPPLIER]
    -> AttributeCreator

Bookmark: Validation HTML
FilenamePartExtractor
    DIRNAME_ATTR = _dirname
    DIRPATH_ATTR = _dirpath
    EXTENSION_ATTR = _extension
    FULLNAME_ATTR = _filename
    ROOTNAME_ATTR = _rootname
    SRC_ATTR = $(InformationContainer)
    -> HTMLReportGenerator_2
HTMLReportGenerator_2
    CONTENT_LIST = HEADER HEADER
    GROUP_BY = Order LacesPublication LacesUri
    PAGE_CONFIG = HEADER{{TEXT;Statistics Report for Information Container;HEADER;H1;HEADER_ID;;ALIGNMENT;LEFT;COLOR;0,0,0;FME_CONTROLLER_QUERY_FILE;transformers/dependencies/html5/Header.fme;FME_CONTROLLER_CHOICE;Header}}HEADER{{TEXT;Supplied Information Container: @Value(_filename);HEADER;H6;HEADER_ID;;ALIGNMENT;LEFT;COLOR;0,0,0;FME_CONTROLLER_QUERY_FILE;transformers/dependencies/html5/Header.fme;FME_CONTROLLER_CHOICE;Header}}
    -> Sorter
HTMLReportGenerator
    CONTENT_LIST = HEADER HEADER HTML
    GROUP_BY = Order QueryName LacesPublication LacesUri
    PAGE_CONFIG:
      HEADER{{TEXT;@Value(QueryName);HEADER;H3;HEADER_ID;;ALIGNMENT;LEFT;COLOR;0,0,0;FME_CONTROLLER_QUERY_FILE;transformers/dependencies/html5/Header.fme;FME_CONTROLLER_CHOICE;Header}}HEADER{{TEXT;@Value(Explanation);HEADER;NO;HEADER_ID;;ALIGNMENT;LEFT;COLOR;0,0,0;FME_CONTROLLER_QUERY_FILE;transformers/dependencies/html5/Header.fme;FME_CONTROLLER_CHOICE;Header}}HTML{{HTML;<div style="padding:10px;border: 1px none black">
         <pre class="tsv-data">@Value(_response_body)</pre>
      </div>;FME_CONTROLLER_QUERY_FILE;transformers/dependencies/html5/Custom HTML.fme;FME_CONTROLLER_CHOICE;Custom HTML}}
    -> Sorter
Sorter
    SORT_PARM = Order NUMERIC ASCENDING
    SORTED -> HTMLLayouter
HTMLLayouter
    DIV_STYLE = NONE
    GROUP_BY = LacesPublication LacesUri
    LAYOUT = VERTICAL
    -> StringReplacer
Note: https://gemini.google.com/share/ac12573da734
StringReplacer
    CASE = NO
    FIND_TEXT = </head>
    NO_MATCH = _FME_NO_OP_
    REGEXP = NO
    REPLACE_TEXT:
      <style>
          /* Force left alignment and styling for the generated tables */
          .sparql-rendered-table {
              margin-left: 0 !important;
              margin-right: auto !important;
              width: auto !important; /* Table only as wide as content */
              min-width: 400px;
              font-size: 0.9rem;
              background-color: white;
          }
          .sparql-rendered-table th, .sparql-rendered-table td {
              text-align: left !important;
              padding: 8px 12px !important;
          }
          .sparql-rendered-table thead th {
              background-color: #f8f9fa;
              border-bottom: 2px solid #dee2e6;
          }
      </style>

      <script>
      document.addEventListener("DOMContentLoaded", function() {
          // Select all pre blocks containing your TSV data
          const tsvBlocks = document.querySelectorAll('pre.tsv-data');

          tsvBlocks.forEach(block => {
              const rawContent = block.innerText.trim();
              if (!rawContent) return;

              const lines = rawContent.split('\n');
              const table = document.createElement('table');

              // Apply Bootstrap classes for outlining and styling
              table.className = "table table-bordered table-hover table-sm sparql-rendered-table";

              const thead = document.createElement('thead');
              const tbody = document.createElement('tbody');

              lines.forEach((line, index) => {
                  const columns = line.split('\t');
                  const tr = document.createElement('tr');

                  columns.forEach(col => {
                      const cell = document.createElement(index === 0 ? 'th' : 'td');
                      let val = col.trim();

                      // Handle URIs: Remove < > and make them clickable links
                      if (val.startsWith('<') && val.endsWith('>')) {
                          const url = val.slice(1, -1);
                          cell.innerHTML = `<a href="${url}" target="_blank">${url}</a>`;
                      } else {
                          cell.textContent = val;
                      }
                      tr.appendChild(cell);
                  });

                  if (index === 0) thead.appendChild(tr);
                  else tbody.appendChild(tr);
              });

              table.appendChild(thead);
              table.appendChild(tbody);

              // Replace the raw <pre> block with the new <table>
              block.parentNode.replaceChild(table, block);
          });
      });
      </script>
      </head>
    SRC_ATTRS = html_content
    -> HTML (writer HTML_1)
    -> HTTPCaller_2
HTML (writer HTML_1)
    attributes: html_content buffer
Note: Delete Publication
HTTPCaller_2
    AUTH_METHOD_TYPE = BASIC
    AUTH_PASSWORD = $(AUTH_PASSWORD)
    AUTH_USERNAME = $(AUTH_USERNAME)
    CONNECTION_TIMEOUT_LENGTH = 60
    CONTENT_TYPE_LOOKUP = text/plain
    ERROR_ATTR = _error
    FOLLOW_REDIRECTS = FOLLOW_WITH_ORIGINAL_METHOD
    HTTP_METHOD = DELETE
    MAX_HTTP_VERSION = HTTP_2
    MAX_TRANSFERS_IN_PROGRESS = 1
    REDIRECT_AUTH = ORIGINAL_DOMAIN_ONLY
    RESPONSE_HEADER_LIST_ATTR = _http
    SAVE_FILE_LOOKUP = NO
    STATUS_CODE_ATTR = _http_status_code
    TARGET_ATTR = _response_body
    TARGET_ATTR_ENCODING = auto-detect
    TARGET_URL = $(LACES_BASE_URL)/api/v3/publications/@Value(LacesPublication)
    TRANSFER_TIMEOUT_LENGTH = 90
    UPLOAD_TYPE = Specify Upload Body
    USE_COOKIES = No
    VERIFY_SSL_CERTIFICATES = Yes
    AUTH_METHOD = Basic
    SAVE_FILE = Attribute
    UPLOAD_CONTENT_TYPE = Text (text/plain)

Bookmark: Run SPARQL
FeatureMerger
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> HTTPCaller_6
Note: Run SPARQL query
HTTPCaller_6
    AUTH_METHOD_TYPE = BASIC
    AUTH_PASSWORD = $(AUTH_PASSWORD)
    AUTH_USERNAME = $(AUTH_USERNAME)
    CONNECTION_TIMEOUT_LENGTH = 60
    CONTENT_TYPE_LOOKUP = application/sparql-query
    CUSTOM_HEADERS = Accept;text/tab-separated-values
    ERROR_ATTR = _error
    FOLLOW_REDIRECTS = FOLLOW_WITH_ORIGINAL_METHOD
    HTTP_METHOD = POST
    MAX_HTTP_VERSION = HTTP_2
    MAX_TRANSFERS_IN_PROGRESS = 1
    REDIRECT_AUTH = ORIGINAL_DOMAIN_ONLY
    SAVE_FILE_LOOKUP = NO
    STATUS_CODE_ATTR = _http_status_code
    TARGET_ATTR = _response_body
    TARGET_ATTR_ENCODING = auto-detect
    TARGET_URL = $(LACES_BASE_URL)@Value(LacesUri)/sparql
    TRANSFER_TIMEOUT_LENGTH = 90
    UPLOAD_BODY = @Value(Query)
    UPLOAD_TYPE = Specify Upload Body
    USE_COOKIES = No
    VERIFY_SSL_CERTIFICATES = Yes
    AUTH_METHOD = Basic
    SAVE_FILE = Attribute
    UPLOAD_CONTENT_TYPE = application/sparql-query
    -> StringReplacer_15
StringReplacer_15
    CASE = NO
    FIND_TEXT = &
    NO_MATCH = _FME_NO_OP_
    REGEXP = NO
    REPLACE_TEXT = &amp;
    SRC_ATTRS = _response_body
    -> StringReplacer_14
StringReplacer_14
    CASE = NO
    FIND_TEXT = <
    NO_MATCH = _FME_NO_OP_
    REGEXP = NO
    REPLACE_TEXT = &lt;
    SRC_ATTRS = _response_body
    -> HTMLReportGenerator
