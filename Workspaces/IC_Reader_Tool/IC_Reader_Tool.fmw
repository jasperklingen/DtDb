FME workspace IC_Reader_Tool.fmw
Usage: If you want to add a new category, just add a new value in the parameter and use that same string in the config, you will be able to filter on just that query

Parameters:
- RUN_UUID:   # UUID
      import fme
      from uuid import uuid4
      
      return str(uuid4())
- Category = VS2   # Select Category
- InformationContainer = C:\Users\JasperKlingenAvineon\Downloads\IC_B6.0_ContractExample.zip   # IC Path
- SYSTEM =   # System Parameters
- LACES_CONNECTION = TenneT Laces
- LACES_REPO = 1fe0104d-14c0-461e-9234-af1b8bf03b7a   # Laces Repository
- LACES_BASE_URL = https://hub.laces.tech   # Laces Base URL
- OUT_HTML = ICReport.html   # Destination Html File
- SourceDataset_XLSXR = C:\Users\JasperKlingenAvineon\OneDrive - Avineon-Tensing\Documents\Tennet Opdracht Oscar\April 2026\IC_Reader_Tool_Config_v5.xlsx   # Source Microsoft Excel File(s)

Readers:
- XLSXR_1: XLSXR from $(SourceDataset_XLSXR)

Writers:
- HTML_1: HTML to $(OUT_HTML)

AttributeCreator
    ATTR_TABLE:
      SET_TO Order (uint8) = 0
      SET_TO CategoryDisplay (varchar(200)) = FME_CONDITIONAL:DEFAULT_VALUE'$(Category)'BOOL_OP;OR;COMPOSITE_TEST;1;TEST $(Category) = 0'All'FME_NUM_CONDITIONS2___
    -> FilenamePartExtractor
Config (reader XLSXR_1)
    attributes: Order number(2,0), Query char(806), QueryTitle char(56), Explanation char(87), Type char(5), Category char(3), Headers char(24)
    -> NullAttributeMapper
Note: No filled in header means query is misc
NullAttributeMapper_Category
    ATTRCHOICE_ACTION = SELECTED
    ATTRLIST = Headers
    NEW_VALUE = Misc
    NULL_TREATMENT_LU = SETVALUE
    SOURCE_ATTR_VAL_LU = SETNULL EMPTY MISSINGATTR
    ATTRCHOICE = Selected Attributes
    NULL_TREATMENT = New Value
    SOURCE_ATTR_VAL = Null Empty "Missing (Selected Attributes Only)"
    -> FeatureMerger [REQUESTOR]

Bookmark: TTL to hub.laces
Creator
    GEOMTYPE = Geometry Object
    NUM = 1
    CREATED -> AC_PathWindows
AC_PathWindows: AttributeCreator
    ATTR_TABLE = SET_TO path_windows (varchar(200)) = $(InformationContainer)
    -> PythonCaller
Note: Combine Graphs
PythonCaller
    NEW_ATTRIBUTES = graph buffer
    PYTHONSOURCE:
      import os
      import zipfile
      import tempfile
      from pathlib import Path
      import fme
      from fme import BaseTransformer
      import fmeobjects
      from rdflib import Graph

      class FeatureProcessor(BaseTransformer):

          def __init__(self):
              self.feature_list = []

          def has_support_for(self, support_type: int):
              return support_type == fmeobjects.FME_SUPPORT_FEATURE_TABLE_SHIM

          def input(self, feature: fmeobjects.FMEFeature):
              self.feature_list.append(feature.getAttribute('path_windows'))

          def close(self):
              pass

          def process_group(self):
              graph = Graph()
              newFeature = fmeobjects.FMEFeature()
              for path in self.feature_list:
                  ext = os.path.splitext(path)[1].lower()

                  if ext == '.ttl':
                      with open(path, 'r', encoding='utf-8') as f:
                          g = Graph()
                          g.parse(data=f.read(), format="turtle")
                          graph = graph + g

                  elif ext == '.zip':
                      temp_dir = tempfile.mkdtemp()
                      with zipfile.ZipFile(path, 'r') as zf:
                          zf.extractall(temp_dir)
                      for root, dirs, files in os.walk(temp_dir):
                          for fname in files:
                              if fname.lower().endswith('.ttl'):
                                  ttl_path = os.path.join(root, fname)
                                  with open(ttl_path, 'r', encoding='utf-8') as f:
                                      g = Graph()
                                      g.parse(data=f.read(), format="turtle")
                                      graph = graph + g

              newFeature.setAttribute("graph", graph.serialize(format="turtle"))
              self.pyoutput(newFeature)

          def reject_feature(self, feature, code, message):
              feature.setAttribute("fme_rejection_code", code)
              feature.setAttribute("fme_rejection_message", message)
              self.pyoutput(feature, output_tag="<Rejected>")
    PYTHONSYMBOL = FeatureProcessor
    -> TempPathnameCreator
TempPathnameCreator
    PATHNAME_ATTR = _pathname
    -> AttributeCreator_25
Note: Publication Metadata
AttributeCreator_25
    ATTR_TABLE:
      SET_TO _uuid = $(RUN_UUID)
      SET_TO metadataJSON = {
            "publicationUri": "@Value(_uuid)",
            "name": "@Value(_uuid)",
            "description": "Dataset for statistics (@Value(_uuid))",
            "owner": "TenneT",
            "publisher": "FME",
            "versioningMode": "NONE",
            "versionLabel": "",
            "schemaURIs": [ ]
        }
      SET_TO file_path = @Value(_pathname)\@Value(_uuid).ttl
    -> AttributeFileWriter
AttributeFileWriter
    CHAR_ENCODING = utf-8
    FILE_NAME = @Value(file_path)
    OVERWRITE_FILE_LOOKUP = DestWriteSrcRead
    SOURCE_ATTR = graph
    OVERWRITE_FILE = Overwrite file
    -> AttributeRemover
Note: Cleanup "graph'so it doesnt dump this in the log when HTTPCaller fails
AttributeRemover
    REMOVE_ATTRS = graph
    -> HTTPCaller_5
Note: Upload to Laces
HTTPCaller_5
    AUTH_METHOD_TYPE = NC
    AUTH_NAMED_CONNECTION = $(LACES_CONNECTION)
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    MULTIPARTS = metadata StringUpload SOURCE_EXPRESSION;@Value(metadataJSON);MIME_TYPE;application/json;FME_CONTROLLER_QUERY_FILE;transformers/dependencies/http/StringUpload.fme;FME_CONTROLLER_CHOICE;StringUpload content FileUpload SOURCE_FILE;@Value(file_path);MIME_TYPE;application/octet-stream;FME_CONTROLLER_QUERY_FILE;transformers/dependencies/http/FileUpload.fme;FME_CONTROLLER_CHOICE;FileUpload
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(LACES_BASE_URL)/api/v3/repositories/$(LACES_REPO)/publications
    TRANSFER_TIMEOUT_LENGTH = 90
    UPLOAD_TYPE = Multipart / Form Data
    USE_COOKIES = No
    VERIFY_SSL_CERTIFICATES = Yes
    AUTH_METHOD = Web Connection
    -> JSONExtractor
JSONExtractor
    EXTRACT_QUERY_TABLE = publication_id json["id"] uri json["uri"]
    JSON_DOCUMENT = @Value(_response_body)
    READ_FROM_FILE = NO
    EVALUATED -> AttributeRenamer_4
AttributeRenamer_4
    ATTR_TABLE:
      RENAME_SET_DEFAULT uri > LacesUri
      RENAME_SET_DEFAULT publication_id > LacesPublication
    KEEP_RENAMED_ONLY = no
    MISSING_INPUT_ATTRS = REMOVE
    -> AttributeKeeper_4
AttributeKeeper_4
    CREATE_BULK_MODE_FEATURES = NO
    KEEP_ATTRS = LacesPublication,LacesUri
    -> FeatureMerger [SUPPLIER]
    -> AttributeCreator

Bookmark: Validation HTML
FilenamePartExtractor
    DIRNAME_ATTR = _dirname
    DIRPATH_ATTR = _dirpath
    EXTENSION_ATTR = _extension
    FULLNAME_ATTR = _filename
    ROOTNAME_ATTR = _rootname
    SRC_ATTR = $(InformationContainer)
    -> HTMLReportGenerator_2
HTMLReportGenerator_2
    CONTENT_LIST = HEADER HEADER HEADER
    GROUP_BY = Order LacesPublication LacesUri
    PAGE_CONFIG = HEADER{{TEXT;Statistics Report for Information Container;HEADER;H1;HEADER_ID;;ALIGNMENT;LEFT;COLOR;0,0,0;FME_CONTROLLER_QUERY_FILE;transformers/dependencies/html5/Header.fme;FME_CONTROLLER_CHOICE;Header}}HEADER{{TEXT;Supplied Information Container: @Value(_filename);HEADER;H6;HEADER_ID;;ALIGNMENT;LEFT;COLOR;0,0,0;FME_CONTROLLER_QUERY_FILE;transformers/dependencies/html5/Header.fme;FME_CONTROLLER_CHOICE;Header}}HEADER{{TEXT;Category: @Value(CategoryDisplay);HEADER;H6;HEADER_ID;;ALIGNMENT;LEFT;COLOR;0,0,0;FME_CONTROLLER_QUERY_FILE;transformers/dependencies/html5/Header.fme;FME_CONTROLLER_CHOICE;Header}}
    -> Sorter
HTMLReportGenerator
    CONTENT_LIST = HEADER HEADER HTML
    GROUP_BY = Order QueryTitle LacesPublication LacesUri
    PAGE_CONFIG:
      HEADER{{TEXT;@Value(QueryTitle);HEADER;H3;HEADER_ID;;ALIGNMENT;LEFT;COLOR;0,0,0;FME_CONTROLLER_QUERY_FILE;transformers/dependencies/html5/Header.fme;FME_CONTROLLER_CHOICE;Header}}HEADER{{TEXT;@Value(Explanation);HEADER;NO;HEADER_ID;;ALIGNMENT;LEFT;COLOR;0,0,0;FME_CONTROLLER_QUERY_FILE;transformers/dependencies/html5/Header.fme;FME_CONTROLLER_CHOICE;Header}}HTML{{HTML;<div style="padding:10px;border: 1px none black" class="@Value(Headers)">
         <pre class="tsv-data">@Value(_response_body)</pre>
      </div>;FME_CONTROLLER_QUERY_FILE;transformers/dependencies/html5/Custom HTML.fme;FME_CONTROLLER_CHOICE;Custom HTML}}
    -> Sorter
Sorter
    SORT_PARM = Order NUMERIC ASCENDING
    SORTED -> HTMLLayouter
HTMLLayouter
    DIV_STYLE = NONE
    GROUP_BY = LacesPublication LacesUri
    LAYOUT = VERTICAL
    -> StringReplacer
Note: https://gemini.google.com/share/ac12573da734
StringReplacer
    CASE = NO
    FIND_TEXT = </head>
    NO_MATCH = _FME_NO_OP_
    REGEXP = NO
    REPLACE_TEXT:
        <link href="https://fonts.googleapis.com/css2?family=Plus+Jakarta+Sans:wght@400;500;600&family=DM+Mono:wght@400;500&display=swap" rel="stylesheet">
      <style>
      :root {
        --font-ui:   'Plus Jakarta Sans', sans-serif;
        --font-mono: 'DM Mono', monospace;

        --page:   #edf1f7;
        --card:   #ffffff;
        --border: #b8c4d4;

        --text-primary: #080e18;
        --text-muted:   #5a6878;

        --accent-blue: #1848a0;
        --accent-cyan: #0a7a8e;

        --hover:  #eef2fb;
        --stripe: #f4f7fc;
        --radius: 8px;
      }

      @media (prefers-color-scheme: dark) {
        :root {
          --page:   #080c14;
          --card:   #101624;
          --border: #1e2d45;

          --text-primary: #dce8f8;
          --text-muted:   #384860;

          --accent-blue: #3a78e8;
          --accent-cyan: #20d8a0;

          --hover:  #141e30;
          --stripe: #0c1220;
        }
      }

      *, *::before, *::after { box-sizing: border-box; margin: 0; padding: 0; }

      body {
        background: var(--page);
        color: var(--text-primary);
        font-family: var(--font-ui);
        font-size: 14px;
        line-height: 1.6;
      }

      /* ── Page header ── */
      .rpt-header {
        background: var(--card);
        padding: 24px 40px 20px;
        border-top: 3px solid var(--accent-blue);
        border-bottom: 1px solid var(--border);
        display: flex;
        align-items: center;
        justify-content: space-between;
        gap: 24px;
      }
      .rpt-header-logo {
        height: 36px;
        width: auto;
        flex-shrink: 0;
      }
      .rpt-header-title {
        color: var(--text-primary);
        font-size: 1.4rem;
        font-weight: 600;
        letter-spacing: -0.02em;
        margin-bottom: 6px;
      }
      .rpt-header-meta {
        display: flex;
        flex-wrap: wrap;
        gap: 10px;
        align-items: center;
      }
      .rpt-header-sub {
        color: var(--text-muted);
        font-family: var(--font-mono);
        font-size: 0.78rem;
      }
      .rpt-header-badge {
        font-size: 10px;
        font-weight: 600;
        letter-spacing: 0.4px;
        padding: 2px 8px;
        border-radius: 3px;
        background: var(--note-bg);
        color: var(--accent-blue);
        border: 0.5px solid var(--border);
      }

      /* ── Page content ── */
      .rpt-page {
        max-width: 1080px;
        margin: 0 auto;
        padding: 32px 24px 56px;
      }

      /* ── Section label ── */
      .group-label {
        font-size: 10px;
        font-weight: 600;
        letter-spacing: 0.7px;
        text-transform: uppercase;
        color: var(--text-muted);
        padding-bottom: 8px;
        border-bottom: 1px solid var(--border);
        margin: 32px 0 16px;
      }
      .group-label:first-of-type { margin-top: 0; }

      /* ── Stat grid ── */
      .stat-grid {
        display: grid;
        grid-template-columns: repeat(auto-fill, minmax(190px, 1fr));
        gap: 12px;
        margin-bottom: 12px;
      }

      /* ── Stat card ── */
      .stat-card {
        background: var(--card);
        border-radius: var(--radius);
        border: 0.5px solid var(--border);
        border-left: 4px solid var(--accent-blue);
        padding: 18px 20px 16px;
        transition: transform 0.12s ease, box-shadow 0.12s ease;
      }
      .stat-card:hover {
        transform: translateY(-2px);
        box-shadow: 0 6px 20px rgba(0,0,0,.09);
      }
      .stat-value {
        font-family: var(--font-mono);
        font-size: 2.2rem;
        font-weight: 500;
        color: var(--accent-blue);
        line-height: 1;
        letter-spacing: -0.03em;
        margin-bottom: 8px;
      }
      .stat-label {
        font-size: 0.75rem;
        color: var(--text-muted);
        line-height: 1.35;
        margin-top: 4px;
      }
      .stat-query {
        font-family: var(--font-ui);
        font-size: 0.85rem;
        font-weight: 600;
        color: var(--text-primary);
        margin-top: 6px;
        white-space: nowrap;
        overflow: hidden;
        text-overflow: ellipsis;
      }

      /* ── Table card ── */
      .table-card {
        background: var(--card);
        border-radius: var(--radius);
        border: 0.5px solid var(--border);
        overflow: hidden;
        margin-bottom: 16px;
      }
      .table-card-header {
        padding: 14px 18px 12px;
        border-bottom: 1px solid var(--border);
      }
      .table-card-qname {
        font-family: var(--font-mono);
        font-size: 0.7rem;
        color: var(--accent-cyan);
        margin-bottom: 3px;
      }
      .table-card-desc {
        font-size: 0.85rem;
        color: var(--text-muted);
      }

      /* ── Tables ── */
      .tbl-wrap { overflow-x: auto; }
      .sparql-table {
        width: 100%;
        border-collapse: collapse;
        font-size: 0.85rem;
      }
      .sparql-table thead th {
        background: var(--accent-blue);
        color: #fff;
        font-weight: 600;
        font-size: 0.75rem;
        letter-spacing: 0.05em;
        text-transform: uppercase;
        padding: 10px 14px;
        text-align: left;
        white-space: nowrap;
        border-bottom: 2px solid var(--accent-cyan);
      }
      .sparql-table thead th:first-child { border-left: 4px solid var(--accent-cyan); }
      .sparql-table tbody td {
        padding: 8px 14px;
        text-align: left;
        border-bottom: 1px solid var(--border);
        color: var(--text-primary);
        vertical-align: top;
      }
      .sparql-table tbody td:first-child {
        font-weight: 500;
        border-left: 4px solid transparent;
      }
      .sparql-table tbody tr:nth-child(even) td { background: var(--stripe); }
      .sparql-table tbody tr:hover td { background: var(--hover); }
      .sparql-table tbody tr:last-child td { border-bottom: none; }
      .sparql-table a {
        color: var(--accent-cyan);
        text-decoration: none;
        font-family: var(--font-mono);
        font-size: 0.78em;
        word-break: break-all;
      }
      .sparql-table a:hover { text-decoration: underline; }
      .tbl-row-count {
        font-size: 0.73rem;
        color: var(--text-muted);
        padding: 7px 14px;
        background: var(--stripe);
        border-top: 1px solid var(--border);
      }

      /* ── Footer ── */
      .rpt-footer {
        background: var(--card);
        border-top: 1px solid var(--border);
        padding: 14px 40px;
        display: flex;
        align-items: baseline;
        gap: 16px;
        flex-wrap: wrap;
      }
      .rpt-footer-label {
        font-size: 10px;
        font-weight: 600;
        letter-spacing: 0.6px;
        text-transform: uppercase;
        color: var(--text-muted);
        flex-shrink: 0;
      }
      .rpt-footer-hash {
        font-family: var(--font-mono);
        font-size: 0.7rem;
        color: var(--text-muted);
        word-break: break-all;
      }
      </style>
      <script>
      document.addEventListener("DOMContentLoaded", function () {

        /* ── STEP 1: TSV → tables ── */
        document.querySelectorAll('pre.tsv-data').forEach(block => {
          const raw = block.innerText.trim();
          if (!raw) return;
          const lines = raw.split('\n').map(l => l.trim()).filter(Boolean);
          if (!lines.length) return;

          const table = document.createElement('table');
          table.className = 'sparql-table';
          const thead = document.createElement('thead');
          const tbody = document.createElement('tbody');

          lines.forEach((line, i) => {
            const cols = line.split('\t');
            const tr = document.createElement('tr');
            cols.forEach(col => {
              const cell = document.createElement(i === 0 ? 'th' : 'td');
              const val = col.trim();
              if (val.startsWith('<') && val.endsWith('>')) {
                const url = val.slice(1, -1);
                const a = document.createElement('a');
                a.href = url; a.target = '_blank'; a.rel = 'noopener noreferrer';
                a.textContent = url;
                cell.appendChild(a);
              } else {
                cell.textContent = val;
              }
              tr.appendChild(cell);
            });
            if (i === 0) thead.appendChild(tr); else tbody.appendChild(tr);
          });

          table.appendChild(thead);
          table.appendChild(tbody);
          block.replaceWith(table);
        });

        /* ── STEP 2: Restructure page ── */
        const bodyDivs = Array.from(document.querySelectorAll('body > div'));
        if (bodyDivs.length < 2) return;

        const h1Text  = bodyDivs[0].querySelector('h1,H1')?.textContent.trim() <pipe><pipe> 'Report';
        const h6Nodes = Array.from(bodyDivs[0].querySelectorAll('h6,H6'));

        /* First H6 = container subtitle; any additional H6s become badges (e.g. "VS: 1") */
        const subtitleText = h6Nodes[0]?.textContent.trim() <pipe><pipe> '';
        const badgeTexts   = h6Nodes.slice(1).map(n => n.textContent.trim()).filter(Boolean);

        /* A trailing div holding only bare MD5 hashes (no heading) is a footer payload, not a section */
        const isHashDiv = div => {
          if (div.querySelector('h3,H3')) return false;
          const ps = Array.from(div.querySelectorAll('p'));
          return ps.length > 0 && ps.every(p => /^[a-f0-9]{32}$/i.test(p.textContent.trim()));
        };

        const contentDivs = bodyDivs.slice(1);
        const hashDivs    = contentDivs.filter(isHashDiv);
        const sectionDivs = contentDivs.filter(div => !isHashDiv(div));
        const hashValues  = hashDivs.flatMap(div =>
          Array.from(div.querySelectorAll('p')).map(p => p.textContent.trim())
        );

        /* Parse sections */
        const sections = sectionDivs.map(div => {
          const queryName   = div.querySelector('h3,H3')?.textContent.trim() <pipe><pipe> '';
          const description = div.querySelector('p')?.textContent.trim() <pipe><pipe> '';
          const table       = div.querySelector('table.sparql-table');

          let kind = 'unknown', value = null;
          if (table) {
            const cols = table.querySelectorAll('thead th').length;
            const rows = table.querySelectorAll('tbody tr').length;
            if (cols === 1 && rows === 1) {
              kind  = 'stat';
              value = table.querySelector('tbody td')?.textContent.trim() <pipe><pipe> '—';
            } else {
              kind = 'table';
            }
          }

          const group = div.querySelector('div[class]')?.getAttribute('class')?.trim() <pipe><pipe> 'Other';

          return { queryName, description, table, kind, value, group };
        });

        /* Collect groups in first-appearance order */
        const groupOrder = [];
        const grouped    = {};
        sections.forEach(s => {
          if (!grouped[s.group]) { grouped[s.group] = []; groupOrder.push(s.group); }
          grouped[s.group].push(s);
        });

        /* ── Build new DOM ── */
        const frag = document.createDocumentFragment();

        /* Header */
        const header = document.createElement('div');
        header.className = 'rpt-header';
        header.innerHTML = `
          <div>
            <div class="rpt-header-title">${h1Text}</div>
            <div class="rpt-header-meta">
              ${subtitleText ? `<div class="rpt-header-sub">${subtitleText}</div>` : ''}
              ${badgeTexts.map(b => `<span class="rpt-header-badge">${b}</span>`).join('')}
            </div>
          </div>
          <img class="rpt-header-logo" src="data:image/svg+xml;base64,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" alt="TenneT">
        `;
        frag.appendChild(header);

        const page = document.createElement('div');
        page.className = 'rpt-page';

        groupOrder.forEach(groupName => {
          const items = grouped[groupName];
          if (!items.length) return;

          const lbl = document.createElement('div');
          lbl.className = 'group-label';
          lbl.textContent = groupName;
          page.appendChild(lbl);

          const stats  = items.filter(i => i.kind === 'stat');
          const tables = items.filter(i => i.kind === 'table');

          if (stats.length) {
            const grid = document.createElement('div');
            grid.className = 'stat-grid';
            stats.forEach(({ queryName, description, value }) => {
              const card = document.createElement('div');
              card.className = 'stat-card';
              card.innerHTML = `
                <div class="stat-value">${value}</div>
                <div class="stat-query">${queryName}</div>
                <div class="stat-label">${description}</div>
              `;
              grid.appendChild(card);
            });
            page.appendChild(grid);
          }

          tables.forEach(({ queryName, description, table }) => {
            const rowCount = table.querySelectorAll('tbody tr').length;
            const card = document.createElement('div');
            card.className = 'table-card';

            const cardHeader = document.createElement('div');
            cardHeader.className = 'table-card-header';
            cardHeader.innerHTML = `
              <div class="table-card-qname">${queryName}</div>
              <div class="table-card-desc">${description}</div>
            `;

            const wrap = document.createElement('div');
            wrap.className = 'tbl-wrap';
            wrap.appendChild(table);

            const rowBadge = document.createElement('div');
            rowBadge.className = 'tbl-row-count';
            rowBadge.textContent = `${rowCount} row${rowCount !== 1 ? 's' : ''}`;

            card.appendChild(cardHeader);
            card.appendChild(wrap);
            card.appendChild(rowBadge);
            page.appendChild(card);
          });
        });

        frag.appendChild(page);

        if (hashValues.length) {
          const footer = document.createElement('div');
          footer.className = 'rpt-footer';
          footer.innerHTML = `
            <span class="rpt-footer-label">MD5</span>
            ${hashValues.map(h => `<span class="rpt-footer-hash">${h}</span>`).join('')}
          `;
          frag.appendChild(footer);
        }

        document.body.innerHTML = '';
        document.body.appendChild(frag);
      });
      </script>
      </head>
    SRC_ATTRS = html_content
    -> HTML (writer HTML_1)
    -> HTTPCaller_2
HTML (writer HTML_1)
    attributes: html_content buffer
Note: Delete Publication
HTTPCaller_2
    AUTH_METHOD_TYPE = NC
    AUTH_NAMED_CONNECTION = $(LACES_CONNECTION)
    CONNECTION_TIMEOUT_LENGTH = 60
    CONTENT_TYPE_LOOKUP = text/plain
    ERROR_ATTR = _error
    FOLLOW_REDIRECTS = FOLLOW_WITH_ORIGINAL_METHOD
    HTTP_METHOD = DELETE
    MAX_HTTP_VERSION = HTTP_2
    MAX_TRANSFERS_IN_PROGRESS = 1
    REDIRECT_AUTH = ORIGINAL_DOMAIN_ONLY
    RESPONSE_HEADER_LIST_ATTR = _http
    SAVE_FILE_LOOKUP = NO
    STATUS_CODE_ATTR = _http_status_code
    TARGET_ATTR = _response_body
    TARGET_ATTR_ENCODING = auto-detect
    TARGET_URL = $(LACES_BASE_URL)/api/v3/publications/@Value(LacesPublication)
    TRANSFER_TIMEOUT_LENGTH = 90
    UPLOAD_TYPE = Specify Upload Body
    USE_COOKIES = No
    VERIFY_SSL_CERTIFICATES = Yes
    AUTH_METHOD = Web Connection
    SAVE_FILE = Attribute
    UPLOAD_CONTENT_TYPE = Text (text/plain)

Bookmark: VS selection
Note: To make backwards compatible with config V4
NullAttributeMapper
    ATTRCHOICE_ACTION = SELECTED
    ATTRLIST = Category
    NEW_VALUE = 0
    NULL_TREATMENT_LU = SETVALUE
    SOURCE_ATTR_VAL_LU = SETNULL EMPTY MISSINGATTR
    ATTRCHOICE = Selected Attributes
    NULL_TREATMENT = New Value
    SOURCE_ATTR_VAL = Null Empty "Missing (Selected Attributes Only)"
    -> T_Catagory_Selection
Note: Filters out Queries based on config and parameters match
Note: If you want to add a new Catagory, Just add it to the config and add it to the Parameter options
Note: If Parameter is both (0) every query is used. If parameter 1 or 2 is selected. Only queries with VS 1 or 2 are excecuted. If a Query has no Category version or null or missing, it is excecuted in both cases
T_Catagory_Selection: Tester
    BOOL_OP = OR
    TEST_CLAUSE:
      TEST @Value(Category) = $(Category)
      TEST @Value(Category) = 0
      TEST $(Category) = 0
    TEST_MODE = TEST
    PASSED -> NullAttributeMapper_Category

Bookmark: Run SPARQL
FeatureMerger
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> HTTPCaller_6
Note: Run SPARQL query
HTTPCaller_6
    AUTH_METHOD_TYPE = NC
    AUTH_NAMED_CONNECTION = $(LACES_CONNECTION)
    CONNECTION_TIMEOUT_LENGTH = 60
    CONTENT_TYPE_LOOKUP = application/sparql-query
    CUSTOM_HEADERS = Accept;text/tab-separated-values
    ERROR_ATTR = _error
    FOLLOW_REDIRECTS = FOLLOW_WITH_ORIGINAL_METHOD
    HTTP_METHOD = POST
    MAX_HTTP_VERSION = HTTP_2
    MAX_TRANSFERS_IN_PROGRESS = 1
    REDIRECT_AUTH = ORIGINAL_DOMAIN_ONLY
    SAVE_FILE_LOOKUP = NO
    STATUS_CODE_ATTR = _http_status_code
    TARGET_ATTR = _response_body
    TARGET_ATTR_ENCODING = auto-detect
    TARGET_URL = $(LACES_BASE_URL)@Value(LacesUri)/sparql
    TRANSFER_TIMEOUT_LENGTH = 90
    UPLOAD_BODY = @Value(Query)
    UPLOAD_TYPE = Specify Upload Body
    USE_COOKIES = No
    VERIFY_SSL_CERTIFICATES = Yes
    AUTH_METHOD = Web Connection
    SAVE_FILE = Attribute
    UPLOAD_CONTENT_TYPE = application/sparql-query
    -> StringReplacer_15
StringReplacer_15
    CASE = NO
    FIND_TEXT = &
    NO_MATCH = _FME_NO_OP_
    REGEXP = NO
    REPLACE_TEXT = &amp;
    SRC_ATTRS = _response_body
    -> StringReplacer_14
StringReplacer_14
    CASE = NO
    FIND_TEXT = <
    NO_MATCH = _FME_NO_OP_
    REGEXP = NO
    REPLACE_TEXT = &lt;
    SRC_ATTRS = _response_body
    -> HTMLReportGenerator
    -> StringReplacer_2

Bookmark: Create hash of filename + date + response bodies of all query's
StringReplacer_2
    CASE = NO
    FIND_TEXT = [\r\n]+
    NO_MATCH = _FME_NO_OP_
    REGEXP = YES
    SRC_ATTRS = _response_body
    TEST_STRING = "\n"
    -> Sorter_2
AttributeRenamer
    ATTR_TABLE = RENAME_SET_DEFAULT datefilename > _response_body
    KEEP_RENAMED_ONLY = no
    MISSING_INPUT_ATTRS = REMOVE
    -> Sorter_2
Sorter_2
    SORT_PARM = Order NUMERIC ASCENDING
    SORTED -> Aggregator
Aggregator
    ACCUM_ATTRS = All
    AGGREGATE_TYPE = Homogeneous Collection (If Possible)
    CONCAT_ATTRS = _response_body
    MODE = Geometry - Assemble One Level
    AGGREGATE -> CRCCalculator_2
CRCCalculator_2
    ALG_TYPE = MD5
    CALC_ATTRS = _response_body
    CRC_ATTR = secondhash
    CRC_TYPE = ATTRIBUTES_ENCODED
    ALG_CHOICES = MD5
    -> Aggregator_2

Bookmark: Create hash of Filename + date as string
Creator_2
    GEOMTYPE = Geometry Object
    NUM = 1
    CREATED -> FilenamePartExtractor_2
FilenamePartExtractor_2
    DIRNAME_ATTR = _dirname
    DIRPATH_ATTR = _dirpath
    EXTENSION_ATTR = _extension
    FULLNAME_ATTR = _filename
    ROOTNAME_ATTR = _rootname
    SRC_ATTR = $(InformationContainer)
    -> AttributeCreator_2
AttributeCreator_2
    ATTR_TABLE:
      SET_TO Order (uint8) = 100
      SET_TO datefilename (varchar(200)) = @DateTimeParse(@DateTimeNow(),%Y%m%d)@Value(_filename)
    -> CRCCalculator
    -> AttributeRenamer
CRCCalculator
    ALG_TYPE = MD5
    CALC_ATTRS = datefilename
    CRC_ATTR = firsthash
    CRC_TYPE = ATTRIBUTES_ENCODED
    ALG_CHOICES = MD5
    -> Aggregator_2

Bookmark: Make Hash footer
Aggregator_2
    ACCUM_ATTRS = All
    AGGREGATE_TYPE = Homogeneous Collection (If Possible)
    MODE = Geometry - Assemble One Level
    SEP = ,
    AGGREGATE -> HTMLReportGenerator_3
HTMLReportGenerator_3
    CONTENT_LIST = HEADER HEADER
    GROUP_BY = Order LacesPublication LacesUri
    PAGE_CONFIG = HEADER{{TEXT;@Value(firsthash);HEADER;NO;HEADER_ID;;ALIGNMENT;LEFT;COLOR;0,0,0;FME_CONTROLLER_QUERY_FILE;transformers/dependencies/html5/Header.fme;FME_CONTROLLER_CHOICE;Header}}HEADER{{TEXT;@Value(secondhash);HEADER;NO;HEADER_ID;;ALIGNMENT;LEFT;COLOR;0,0,0;FME_CONTROLLER_QUERY_FILE;transformers/dependencies/html5/Header.fme;FME_CONTROLLER_CHOICE;Header}}
    -> Sorter
