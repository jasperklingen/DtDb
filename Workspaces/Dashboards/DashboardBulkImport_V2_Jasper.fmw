FME workspace DashboardBulkImport_V2_Jasper.fmw

Parameters:
- DestDataset_HTML = C:\Users\JasperKlingenAvineon\OneDrive - Avineon-Tensing\Documents\Tennet Opdracht Oscar\April 2026   # Destination Html Folder

Writers:
- HTML_1: HTML to $(DestDataset_HTML)

JSONExtractor
    EXTRACT_QUERY_TABLE = inputJSON json["publishedParameters"]["InputJSON"] relaticsUUID json["publishedParameters"]["REL_WORKSPACE"]
    JSON_DOCUMENT = @Value(_response_body)
    READ_FROM_FILE = NO
    EVALUATED -> AttributeFilter
AttributeFilter
    ATTR_NAME = status
    ATTR_VALUES = <Empty>,<Missing>,<Null>,<Unfiltered>,success,failed,running,queued
    success -> DateTimeCalculator
    failed -> DateTimeCalculator
    running -> DateTimeConverter_3
    queued -> DateTimeConverter_4
Tester
    BOOL_OP = OR
    TEST_CLAUSE = TEST parentJob ATTRIBUTE_HAS_A_VALUE ""
    TEST_MODE = TEST
    PASSED -> JSONExtractor_2
    FAILED -> AttributeCreator
JSONExtractor_2
    EXTRACT_QUERY_TABLE = order json["order"] query json["query"] endpoint json["endpoint"] filename json["filename"] operation json["operation"]
    JSON_DOCUMENT = @Value(inputJSON)
    READ_FROM_FILE = NO
    EVALUATED -> Sorter
Sorter
    SORT_PARM = parentJob NUMERIC DESCENDING id NUMERIC DESCENDING
    SORTED -> HTMLReportGenerator_2
HTMLReportGenerator_2
    CONTENT_LIST = TABLE
    GROUP_BY = parentJob
    PAGE_CONFIG = TABLE{{STYLE;DEFAULT;TABLE;id|JobId/operation|Operation/status|Status/timeStarted|Tijd van starten/timeFinished|Tijd van afronding/elapsedTime|Benodigde tijd;FME_CONTROLLER_QUERY_FILE;transformers/dependencies/html5/Table.fme;FME_CONTROLLER_CHOICE;Table}}
    -> StringSearcher_2
StringSearcher_2
    CASE = no
    MATCHED_RESULT_ATTR = _html_table
    REGEXP = <table.+</table>
    STRING_TO_SEARCH = @Value(html_content)
    MATCHED -> FeatureJoiner [LEFT]
Note: Relatics URL a href
AttributeCreator
    ATTR_TABLE = SET_TO relaticsUrl (varchar(200)) = <a href="https://tennet.relaticsonline.com/@Value(relaticsUUID)" target="_blank">@Value(relaticsUUID)</a>
    -> FeatureJoiner [RIGHT]
    -> Sorter_3
FeatureJoiner
    ATTR_CONFLICT_RES_LOOKUP = USE_RIGHT
    GEOMETRY_HANDLING_LOOKUP = USE_LEFT
    JOIN_KEYS = parentJob id AUTO
    JOIN_MODE = Inner
    ATTR_CONFLICT_RES = Prefer Right
    GEOMETRY_HANDLING = Prefer Left
    JOINED -> Sorter_2
    UNJOINED_RIGHT -> AttributeCreator_4
AttributeCreator_4
    ATTR_TABLE = SET_TO parentJob (varchar(200)) = @Value(id)
    -> Sorter_2
Sorter_2
    SORT_PARM = parentJob NUMERIC DESCENDING
    SORTED -> HTMLReportGenerator_3
HTMLReportGenerator_3
    CONTENT_LIST = HTML
    GROUP_BY = parentJob
    PAGE_CONFIG:
      HTML{{HTML;<div>
          <h4>@Value(sourceName)</h4>
          Job ID: <a href="https://tennet.vicrea.nl/fmeserver/job/@Value(id)/summary" target="_blank">@Value(id)</a>
          <br>
          Runtime user: <strong>@Value(runtimeUserName)</strong>
          <br>
          Relatics Workspace: @Value(relaticsUrl)
          <br>
          Status: <strong>@Value(status)</strong>
          <br>
          Tijd van toevoegen: @Value(timeQueued)
          <br>
          Tijd van starten: @Value(timeStarted)
          <br>
          Tijd van afronding: @Value(timeFinished)
          <br>
          Totale tijd: @Value(elapsedTime)
          @Value(_html_table)
      </div>;FME_CONTROLLER_QUERY_FILE;transformers/dependencies/html5/Custom HTML.fme;FME_CONTROLLER_CHOICE;Custom HTML}}
    -> Sorter_4
Sorter_4
    SORT_PARM = parentJob NUMERIC DESCENDING
    SORTED -> HTMLLayouter_2
HTMLLayouter_2
    DIV_STYLE = VERTICAL
    LAYOUT = VERTICAL
    TITLE = BulkImportDashboard
    -> StringReplacer_4
StringReplacer_4
    CASE = NO
    FIND_TEXT = <body>
    NO_MATCH = _FME_NO_OP_
    REGEXP = NO
    REPLACE_TEXT:
      <body>
      <div class="container-fluid mt-3 mb-3">
          <div class="row">
              <div class="col-md-3">
                  <div class="input-group mb-2">
                      <div class="input-group-prepend"><label class="input-group-text">App</label></div>
                      <select class="custom-select filter-input" id="appFilter" data-field="app">
                          <option value="all">All Apps</option>
                      </select>
                  </div>
              </div>
              <div class="col-md-3">
                  <div class="input-group mb-2">
                      <div class="input-group-prepend"><label class="input-group-text">User</label></div>
                      <select class="custom-select filter-input" id="userFilter" data-field="user">
                          <option value="all">All Users</option>
                      </select>
                  </div>
              </div>
              <div class="col-md-3">
                  <div class="input-group mb-2">
                      <div class="input-group-prepend"><label class="input-group-text">Status</label></div>
                      <select class="custom-select filter-input" id="statusFilter" data-field="status">
                          <option value="all">All Statuses</option>
                      </select>
                  </div>
              </div>
              <div class="col-md-3">
                  <button type="button" class="btn btn-outline-secondary w-100" id="clearFilters">Clear All Filters</button>
              </div>
          </div>
      </div>
    SRC_ATTRS = html_content
    -> StringReplacer_5
StringReplacer_5
    CASE = NO
    FIND_TEXT = </body>
    NO_MATCH = _FME_NO_OP_
    REGEXP = NO
    REPLACE_TEXT:
      <script>
      document.addEventListener('DOMContentLoaded', function() {
          // Select the outer DIVs that wrap each H4 and Table
          const sections = document.querySelectorAll('body > div[style*="padding:10px"]');
          const filters = document.querySelectorAll('.filter-input');
          const clearBtn = document.getElementById('clearFilters');

          const uniqueValues = { app: new Set(), user: new Set(), status: new Set() };

          // 1. Data Extraction
          sections.forEach(section => {
              const h4 = section.querySelector('h4');
              const appName = h4 ? h4.textContent.trim() : "Unknown App";

              // Use regex to find User and Status in the text nodes
              const text = section.innerText;
              const userMatch = text.match(/Runtime user:\s*(.*)/);
              const statusMatch = text.match(/Status:\s*(.*)/);

              const user = userMatch ? userMatch[1].trim() : "Unknown";
              const status = statusMatch ? statusMatch[1].trim() : "Unknown";

              // Store data on the element for filtering
              section.setAttribute('data-app', appName);
              section.setAttribute('data-user', user);
              section.setAttribute('data-status', status);

              uniqueValues.app.add(appName);
              uniqueValues.user.add(user);
              uniqueValues.status.add(status);
          });

          // 2. Populate Dropdowns
          filters.forEach(filter => {
              const field = filter.getAttribute('data-field');
              Array.from(uniqueValues[field]).sort().forEach(val => {
                  const option = document.createElement('option');
                  option.value = val;
                  option.textContent = val;
                  filter.appendChild(option);
              });
          });

          // 3. Multi-Filter Logic
          function applyFilters() {
              const activeFilters = {};
              filters.forEach(f => {
                  if (f.value !== 'all') activeFilters[f.getAttribute('data-field')] = f.value;
              });

              sections.forEach(section => {
                  let isVisible = true;
                  for (const [field, value] of Object.entries(activeFilters)) {
                      if (section.getAttribute(`data-${field}`) !== value) {
                          isVisible = false;
                          break;
                      }
                  }
                  section.style.display = isVisible ? 'block' : 'none';
              });
          }

          // Event Listeners
          filters.forEach(f => f.addEventListener('change', applyFilters));
          clearBtn.addEventListener('click', () => {
              filters.forEach(f => f.value = 'all');
              sections.forEach(section => section.style.display = 'block');
          });
      });
      </script>
      </body>
    SRC_ATTRS = html_content
    -> AttributeCreator_2
AttributeCreator_2
    ATTR_TABLE = SET_TO html_filename (varchar(28)) = BulkImportSOVDashboardTotaal
    -> HTML (writer HTML_1)
Sorter_3
    SORT_PARM = id NUMERIC DESCENDING
    SORTED -> HTMLReportGenerator
Note: Make HTML page from features
HTMLReportGenerator
    CONTENT_LIST = TABLE
    PAGE_CONFIG = TABLE{{STYLE;DEFAULT;TABLE;id|JobId/sourceName|App/runtimeUserName|Runtime User/status|Status/relaticsUrl|Relatics Workspace/timeQueued|Tijd van toevoegen/timeStarted|Tijd van starten/timeFinished|Tijd van afronding/elapsedTime|Benodigde tijd/Repository|Repository;FME_CONTROLLER_QUERY_FILE;transformers/dependencies/html5/Table.fme;FME_CONTROLLER_CHOICE;Table}}
    -> StringReplacer
Note: Adds HTML and JS
StringReplacer
    CASE = NO
    FIND_TEXT = <body>
    NO_MATCH = _FME_NO_OP_
    REGEXP = NO
    REPLACE_TEXT:
      <body>
          <div class="container-fluid mt-3 mb-3">
              <div class="row">
                  <div class="col-md-3">
                      <div class="input-group mb-2">
                          <div class="input-group-prepend"><label class="input-group-text">App</label></div>
                          <select class="custom-select filter-input" id="appFilter" data-col="1">
                              <option value="all">All Apps</option>
                          </select>
                      </div>
                  </div>
                  <div class="col-md-3">
                      <div class="input-group mb-2">
                          <div class="input-group-prepend"><label class="input-group-text">User</label></div>
                          <select class="custom-select filter-input" id="userFilter" data-col="2">
                              <option value="all">All Users</option>
                          </select>
                      </div>
                  </div>
                  <div class="col-md-3">
                      <div class="input-group mb-2">
                          <div class="input-group-prepend"><label class="input-group-text">Status</label></div>
                          <select class="custom-select filter-input" id="statusFilter" data-col="3">
                              <option value="all">All Statuses</option>
                          </select>
                      </div>
                  </div>
                  <div class="col-md-3">
                      <button type="button" class="btn btn-outline-secondary w-100" id="clearFilters">Clear All Filters</button>
                  </div>
              </div>
          </div>

      <script>
          document.addEventListener('DOMContentLoaded', function() {
              const tableRows = document.querySelectorAll('tbody tr');
              const filters = document.querySelectorAll('.filter-input');
              const clearBtn = document.getElementById('clearFilters');

              // Updated indexes: 1=App, 2=User, 3=Status
              const uniqueValues = { 1: new Set(), 2: new Set(), 3: new Set() };

              // 1. Scan Table Rows and store data
              tableRows.forEach(row => {
                  [1, 2, 3].forEach(colIndex => {
                      if (row.cells[colIndex]) {
                          const val = row.cells[colIndex].textContent.trim();
                          uniqueValues[colIndex].add(val);
                          row.setAttribute(`data-col-${colIndex}`, val);
                      }
                  });
              });

              // 2. Populate Dropdowns
              filters.forEach(filter => {
                  const colIndex = filter.getAttribute('data-col');
                  // Sort values alphabetically, handling empty values
                  const sortedValues = Array.from(uniqueValues[colIndex])
                      .filter(v => v !== "")
                      .sort();

                  sortedValues.forEach(val => {
                      const option = document.createElement('option');
                      option.value = val;
                      option.textContent = val;
                      filter.appendChild(option);
                  });
              });

              // 3. Combined Filtering Logic
              function applyFilters() {
                  const activeFilters = {};
                  filters.forEach(f => {
                      if (f.value !== 'all') activeFilters[f.getAttribute('data-col')] = f.value;
                  });

                  tableRows.forEach(row => {
                      let isVisible = true;
                      for (const [colIndex, value] of Object.entries(activeFilters)) {
                          if (row.getAttribute(`data-col-${colIndex}`) !== value) {
                              isVisible = false;
                              break;
                          }
                      }
                      row.style.display = isVisible ? '' : 'none';
                  });
              }

              // Event Listeners
              filters.forEach(f => f.addEventListener('change', applyFilters));

              clearBtn.addEventListener('click', () => {
                  filters.forEach(f => f.value = 'all');
                  tableRows.forEach(row => row.style.display = '');
              });
          });
      </script>
    SRC_ATTRS = html_content
    -> AttributeCreator_3
    -> FeatureWriter [HTML]
AttributeCreator_3
    ATTR_TABLE = SET_TO html_filename (varchar(26)) = BulkImportSOVDashboardApps
    -> HTML (writer HTML_1)
HTML (writer HTML_1)
    attributes: html_content buffer
FeatureWriter
    DATASET = C:\Users\JasperKlingenAvineon\OneDrive - Avineon-Tensing\Documents\Tennet Opdracht Oscar\April 2026\preview.html
    DATASET_ATTR = _dataset
    FEATURE_TYPE_LIST_ATTR = _feature_types
    FORMAT = HTML
    HTML_COORDINATE_SYSTEM_GRANULARITY = FEATURE
    HTML_DESTINATION_DATASETTYPE_VALIDATION = Yes
    HTML_ENCODING = UTF8
    HTML_END_OF_LINE = System
    HTML_MIME_TYPE = text/html
    HTML_OVERWRITE_FILE = YES
    HTML_WRITE_LAST_EOL = YES
    HTML_WRITE_UTF8_BOM = YES
    TOTAL_FEATURES_WRITTEN_ATTR = _total_features_written
Tester_2
    BOOL_OP = OR
    TEST_CLAUSE = TEST @Value(repository) = SOV
    TEST_MODE = TEST

Bookmark: Map Status to Request
Creator
    GEOMTYPE = Geometry Object
    NUM = 4
    CREATED -> AttributeValueMapper
AttributeValueMapper
    LUT = 0,success,1,failure,2,running,3,queued
    MAPPING_DIRECTION = FORWARD
    SRC = _creation_instance
    VAL_ATTR = _status
    -> Cloner

Bookmark: Get Jobs
Cloner
    COPIES = 2
    COPYATT = _copynum
    COPY -> AVM_Repositories
AVM_Repositories: AttributeValueMapper
    LUT = 0,BulkImportRelatics,1,SOV
    MAPPING_DIRECTION = FORWARD
    SRC = _copynum
    VAL_ATTR = Repository
    -> HTTPCaller
Note: Queued/Running/Success/Failure
HTTPCaller
    ADDITIONAL_URL_PARAMETERS = status;@Value(_status) repository;@Value(Repository) limit;1000
    AUTH_METHOD_TYPE = NC
    AUTH_NAMED_CONNECTION = TenneTVicrea
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = ALLOW_LESS_SECURE_ENCRYPTION
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://tennet.vicrea.nl/fmeapiv4/jobs
    TRANSFER_TIMEOUT_LENGTH = 90
    USE_COOKIES = No
    VERIFY_SSL_CERTIFICATES = Yes
    AUTH_METHOD = Web Connection
    -> JSONFragmenter
JSONFragmenter
    EXPLODE_FORMAT = JSON
    EXTRACT_ATTR = Yes
    JSON_ATTR = _response_body
    JSON_QUERY = json["items"][*]
    READ_FROM_FILE = NO
    RECURSIVE = YES
    REJECT_EMPTY_LISTS = NO
    FRAGMENTS -> AttributeExposer
AttributeExposer
    ATTR_TABLE = _creation_instance,uint8,_http_status_code,uint8,_response_body,varchar(938),_status,varchar(7),cpuPercent,real64,cpuTime,uint32,description,varchar(200),elapsedTime,uint32,engineHost,varchar(9),engineName,varchar(23),errorCount,uint8,id,uint16,json_index,uint8,json_type,varchar(6),lineCount,uint16,peakMemoryUsage,uint32,queue,varchar(47),queueType,varchar(6),repository,varchar(18),resultDatasetDownloadUrl,varchar(84),runtimeUserID,varchar(36),runtimeUserName,varchar(22),sourceID,varchar(36),sourceName,varchar(33),sourceType,varchar(13),status,varchar(7),timeFinished,varchar(24),timeQueued,varchar(24),timeStarted,varchar(24),userID,varchar(36),userName,varchar(15),warningCount,uint8,workspace,varchar(46)
    -> StringSearcher

Bookmark: Get Child Jobs
StringSearcher
    CASE = no
    MATCHED_PARTS_ATTR = _submatch
    MATCHED_RESULT_ATTR = _first_match
    REGEXP = .+@(\d+)
    STRING_TO_SEARCH = @Value(engineName)
    MATCHED -> AttributeRenamer
    NOT_MATCHED -> HTTPCaller_2
AttributeRenamer
    ATTR_TABLE = RENAME_SET_DEFAULT _submatch{0}.part > parentJob
    KEEP_RENAMED_ONLY = no
    MISSING_INPUT_ATTRS = REMOVE
    -> HTTPCaller_2
Note: JobInformation
HTTPCaller_2
    ADDITIONAL_URL_PARAMETERS = status;@Value(_status) repository;@Value(repository)
    AUTH_METHOD_TYPE = NC
    AUTH_NAMED_CONNECTION = TenneTVicrea
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://tennet.vicrea.nl/fmeapiv4/jobs/@Value(id)
    TRANSFER_TIMEOUT_LENGTH = 90
    USE_COOKIES = No
    VERIFY_SSL_CERTIFICATES = Yes
    AUTH_METHOD = Web Connection
    -> JSONExtractor
    -> Tester_2

Bookmark: Elapsed Time to hh:mm:ss
DateTimeCalculator
    MODE = DATETIMECALC_1_ADD_INTERVAL
    OPERATION_PARAMETERS = START_DATETIME_DATETIMECALC_1_ADD_INTERVAL]19000101000000]OPERATOR]ADD]YEARS]0]MONTHS]0]DAYS]0]HOURS]0]MINUTES]0]SECONDS]@Value(elapsedTime)/1000]RESULT_DATETIME]elapsedTime]START_DATETIME]19000101000000
    -> AttributeRounder
AttributeRounder
    PLACES = 0
    ROUND_TYPE_TCL = round
    SRC_ATTRS = elapsedTime
    ROUND_TYPE = Nearest
    -> DateTimeConverter
DateTimeConverter
    DATETIME_ATTR = elapsedTime
    IN_FORMAT = %Y%m%d%H%M%S$
    OUT_FORMAT = %H:%M:%S
    PASSTHROUGH = NO
    REPAIR_INPUT = YES
    -> DateTimeConverter_2

Bookmark: TimeFinished/Started/Queued zonder T, en zonder microseconden
DateTimeConverter_2
    DATETIME_ATTR = timeFinished timeQueued timeStarted
    IN_FORMAT = %Y-%m-%dT%H:%M:%SZ
    OUT_FORMAT = %Y-%m-%d %H:%M:%S
    PASSTHROUGH = NO
    REPAIR_INPUT = YES
    -> StringReplacer_2
DateTimeConverter_3
    DATETIME_ATTR = timeQueued timeStarted
    IN_FORMAT = %Y-%m-%dT%H:%M:%SZ
    OUT_FORMAT = %Y-%m-%d %H:%M:%S
    PASSTHROUGH = NO
    REPAIR_INPUT = YES
    -> StringReplacer_2
DateTimeConverter_4
    DATETIME_ATTR = timeQueued
    IN_FORMAT = %Y-%m-%dT%H:%M:%SZ
    OUT_FORMAT = %Y-%m-%d %H:%M:%S
    PASSTHROUGH = NO
    REPAIR_INPUT = YES
    -> StringReplacer_2
StringReplacer_2
    CASE = NO
    FIND_TEXT = \.\d+$
    NO_MATCH = _FME_NO_OP_
    REGEXP = YES
    SRC_ATTRS = timeFinished,timeQueued,timeStarted
    -> NullAttributeMapper
NullAttributeMapper
    ATTRCHOICE_ACTION = SELECTED
    ATTRLIST = elapsedTime timeFinished timeQueued timeStarted
    NULL_TREATMENT_LU = SETNULL
    OTHER_VALUE = 0
    SOURCE_ATTR_VAL_LU = SETNULL
    ATTRCHOICE = Selected Attributes
    NULL_TREATMENT = Null
    SOURCE_ATTR_VAL = Null
    -> Tester
