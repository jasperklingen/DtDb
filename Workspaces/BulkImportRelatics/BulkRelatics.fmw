FME workspace BulkRelatics.fmw

Parameters:
- HEADER = H3   # Validation Header Level
- InputJSON = { "order" : 1, "query" : "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", "endpoint" : "https://hub.laces.tech/tennet/gfo-nl/eu-303/private/live/tennet/library/eu-303-atl/versions/v7_0/sparql?default-graph-uri=http://hub.laces.tech/tennet/gfo-nl/eu-303/private/live/tennet/library/eu-303-vs2/versions/v9_0", "filename" : "8.0_Bulk_VS2_08_VS2SPL_Spec-ActivityRelation+DefinitionFIX.xml", "operation" : "8.0_Bulk_VS2_08_VS2SPL_Spec-ActivityRelation+Definition", "entrycode" : "D9371660733E63C37E5D644AFC5000FA" }   # InputJson
- SPARQL_OUTFOLDER = C:\temp   # Temp folder for SPARQL result
- FANOUT_DIR =   # Destination Fanout Directory
- BATCH_SIZE = 10000   # Batch Size for Relatics
- TARGET_URL = https://tennet.relaticsonline.com/DataExchange.asmx?wsdl   # Request URL
- RelaticsWorkspace = fe576837-086f-476c-8b51-1e9207510b9c   # Relatics Workspace
- AUTH_NAMED_CONNECTION = TenneT Laces   # EXCLUDE_SERVICES:"Amazon Web Services","HDFS Insecure Client","HDFS Delegation Token","HDFS Kerberos" Web Connection
- RETRY_INITIAL_BACKOFF = 5000   # Initial Backoff Time (msec)
- RATE_LIMIT_MAX_REQUESTS = 200   # Maximum Requests per Interval

Writers:
- HTML_1: HTML to $(FANOUT_DIR)

Creator
    GEOMTYPE = Geometry Object
    NUM = 1
    CREATED -> ParameterFetcher
ParameterFetcher
    ATTR_LIST = _InputJSON $(InputJSON)
    -> JSONExtractor
JSONExtractor
    EXTRACT_QUERY_TABLE = Order json["order"] Query json["query"] Endpoint json["endpoint"] Filename json["filename"] Operation json["operation"] Entrycode json["entrycode"]
    JSON_DOCUMENT = @Value(_InputJSON)
    READ_FROM_FILE = NO
    EVALUATED -> TextDecoder
TextDecoder
    ATTR_ENCODING = utf-8
    DEST_ATTR = Query
    ENCODING_TYPE_LOOKUP = BASE64_DECODE
    STRING_TO_DECODE = @Value(Query)
    ENCODING_TYPE = Base64
    -> HTTPCaller_5

Bookmark: 3.1.1 Query
Note: Run SPARQL query
HTTPCaller_5
    AUTH_METHOD_TYPE = NC
    AUTH_NAMED_CONNECTION = $(AUTH_NAMED_CONNECTION)
    CLIENT_CERTIFICATE_TYPE = NONE
    CONNECTION_TIMEOUT_LENGTH = 1200
    CONTENT_TYPE_LOOKUP = application/sparql-query
    CUSTOM_HEADERS = Accept;text/csv Accept-Encoding;gzip,deflate,br
    ERROR_ATTR = _error
    FILE_PATH_ATTR = _response_file_path
    FOLLOW_REDIRECTS = FOLLOW_WITH_ORIGINAL_METHOD
    HTTP_METHOD = POST
    MAX_HTTP_VERSION = HTTP_2
    MAX_TRANSFERS_IN_PROGRESS = 1
    MINIMUM_ENCRYPTION_LEVEL = OS_DEFAULT
    OUTPUT_FILENAME = $(SPARQL_OUTFOLDER)\@Value(Operation).csv
    RATE_LIMIT_INTERVAL_IN_SECONDS = 60
    RATE_LIMIT_MAX_REQUESTS = $(RATE_LIMIT_MAX_REQUESTS)
    RATE_LIMIT_REQUEST_TIMING = BURST
    REDIRECT_AUTH = ORIGINAL_DOMAIN_ONLY
    RESPONSE_HEADER_LIST_ATTR = _headers
    RESPONSE_TYPE = File
    RETRY_FAILED_TRANSFERS = CONNECTION 429
    RETRY_INITIAL_BACKOFF = $(RETRY_INITIAL_BACKOFF)
    RETRY_MAX_RETRIES = 3
    STATUS_CODE_ATTR = _http_status_code
    TARGET_URL = @Value(Endpoint)
    TRANSFER_TIMEOUT_LENGTH = 1200
    UPLOAD_BODY = @Value(Query)
    UPLOAD_TYPE = STRING_UPLOAD
    USE_COOKIES = No
    VERIFY_SSL_CERTIFICATES = No
    AUTH_METHOD = Web Connection
    UPLOAD_CONTENT_TYPE = application/sparql-query
    -> Junction_5
    <REJECTED> -> Junction_5
Junction_5
    -> AttributeKeeper_6

Bookmark: 3.1Export data from hub.Laces
Note: Cleanup
AttributeKeeper_6
    CREATE_BULK_MODE_FEATURES = NO
    KEEP_ATTRS = Entrycode,Filename,Operation,Order,_response_file_path
    -> DateTimeStamper
DateTimeStamper
    DATETIME_ATTR = _timestamp
    INCLUDE_FRAC_SECONDS = YES
    INCLUDE_OFFSET = NO
    SCOPE = feature
    STAMP_TYPE = datetime
    TIMEZONE = utc
    -> FeatureReader [INITIATOR]

Bookmark: Proces CSV for Pre-processing
FeatureReader
    ATTR_ACCUM_MODE = Merge Initiator and Result
    ATTR_CONFLICT_RES = Use Result
    ATTR_IGNORE_NULLS = No
    COMBINE_GEOM = Use Result
    CSV2_CASE_SENSITIVE_FIELD_NAMES = Yes
    CSV2_CHUNK_SIZE = 100000
    CSV2_DATA_START_LINE = 2
    CSV2_DATE_INPUT_FORMAT = %Y-%m-%d$
    CSV2_DELIMITER = ,
    CSV2_DELIMITER_DETECTION_ALGORITHM = EQUAL_FIELDS_PER_LINE
    CSV2_ENCODING = utf-8
    CSV2_ENFORCE_STRICT_SCHEMA = No
    CSV2_FEATURE_TYPE_NAME = FILE_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = @Value(_response_file_path)
    FORMAT = CSV2
    INTERACT = NONE
    OUTPUT_FEATURES_DISPLAY = Schema and Data Features
    <SCHEMA> -> AttributeKeeper
    <OTHER> -> AttributeExposer
AttributeKeeper
    CREATE_BULK_MODE_FEATURES = NO
    KEEP_ATTRS = Operation,Entrycode,Filename,Order,_timestamp
    KEEP_LIST = attribute{}
    -> FeatureMerger_2 [SUPPLIER]
    -> FeatureMerger [SUPPLIER]
AttributeExposer
    ATTR_TABLE = publicationDate,
    -> DateTimeConverter
DateTimeConverter
    DATETIME_ATTR = publicationDate
    IN_FORMAT = %Y%m%d$
    OUT_FORMAT = %Y-%m-%d
    PASSTHROUGH = NO
    REPAIR_INPUT = YES
    -> FeatureMerger [REQUESTOR]
    <REJECTED> -> FeatureMerger [REQUESTOR]
FeatureMerger
    ATTR_ACCUM_MODE = Merge Supplier
    ATTR_CONFLICT_RES_LOOKUP = REQUESTOR_IF_CONFLICT
    GROUP_BY = Operation
    IGNORE_NULLS = No
    JOIN_KEYS = @Value(Operation) @Value(Operation) AUTO
    MERGE_TYPE_VAL = ATTRIBUTES
    PRESERVE_FEATURE_ORDER_LOOKUP = PER_OUTPUT_PORT
    PROCESS_DUPS = NO
    REJECT_NULL_MISSING_KEYS = No
    SUPPLIERS_FIRST = Yes
    ATTR_CONFLICT_RES = Use Requestor
    MERGE_TYPE = Attributes Only
    MERGED -> PythonCaller

Bookmark: 3.2 Pre-Proces Data for Relatics
Note: Remove & and < from attributes values
PythonCaller
    PYTHONSOURCE:
      import fme
      import fmeobjects


      class FeatureProcessor(object):
          """Template Class Interface:
          When using this class, make sure its name is set as the value of the 'Class
          to Process Features' transformer parameter.
          """

          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              sparqlheaders = feature.getAttribute('attribute{}.name')
              for h in sparqlheaders:
                  ### bugfix: string() makes sure that an attribute is always
                  ### replaceable, in case attribute contains only numbers
                  att = str(feature.getAttribute(h))
                  new1 = att.replace('&','&amp;')
                  new2 = new1.replace('<','&lt;')
                  feature.setAttribute(h,new2)

              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> PythonCaller_3
Note: SPARQL CSV row to RelaticsXML Row
PythonCaller_3
    NEW_ATTRIBUTES = _xmlline
    PYTHONSOURCE:
      import fme
      import fmeobjects
      from fmeobjects import FMELogFile
      import re


      class FeatureProcessor(object):
          """Template Class Interface:
          When using this class, make sure its name is set as the value of the 'Class
          to Process Features' transformer parameter.
          """

          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """

              schema = feature.getAttribute('attribute{}.name')
              xmlpart = []
              for attribute in schema:
                 value = feature.getAttribute(attribute)
                 xmlpart.append(attribute.replace("?","")+'="'+re.sub(r'"','',value)+'"')

              xmlline = "<Row "+" ".join(xmlpart)+" />"

              feature.setAttribute('_xmlline',xmlline)
              ##FMELogFile().logMessageString(xmlline,2)
              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> BatchGrouper
BatchGrouper
    GROUP_SIZE = $(BATCH_SIZE)
    VAL_ATTR = _group
    -> StringReplacer_2
StringReplacer_2
    CASE = no
    FIND_TEXT = \.xml$|\.csv$
    NO_MATCH = _FME_NO_OP_
    REGEXP = YES
    SRC_ATTRS = Filename
    -> AttributeCreator
Note: AttributeCreator [AttributeCreator Version 9] / Attributes To Create: New AttributeValuetemp_filename@Value(Filename)_batch$(BATCH_SIZE)-@Value(_group).xml / Latest Version: 10
AttributeCreator
    ATTR_TABLE = SET_TO temp_filename = @Value(Filename)_batch$(BATCH_SIZE)-@Value(_group).xml
    -> FeatureWriter [text_line]
FeatureWriter
    DATASET = $(SPARQL_OUTFOLDER)\@Value(temp_filename)
    DATASET_ATTR = _dataset
    FEATURE_TYPE_LIST_ATTR = _feature_types
    FORMAT = TEXTLINE
    MORE_SUMMARY_ATTRS = _timestamp
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
    SUMMARY -> FilenamePartExtractor
FilenamePartExtractor
    DIRNAME_ATTR = _dirname
    DIRPATH_ATTR = _dirpath
    EXTENSION_ATTR = _extension
    FULLNAME_ATTR = Filename
    ROOTNAME_ATTR = _rootname
    SRC_ATTR = @Value(_dataset)
    -> AttributeFileReader
AttributeFileReader
    CHAR_ENCODING = utf-8
    DEST_ATTR = _file_contents
    FILE_NAME = @Value(_dataset)
    -> FeatureMerger_2 [REQUESTOR]
Note: Suppliers First = Yes
FeatureMerger_2
    ATTR_ACCUM_MODE = Merge Supplier
    ATTR_CONFLICT_RES_LOOKUP = REQUESTOR_IF_CONFLICT
    IGNORE_NULLS = No
    JOIN_KEYS = @Value(_feature_types{0}._timestamp) @Value(_timestamp) AUTO
    MERGE_TYPE_VAL = ATTRIBUTES
    PRESERVE_FEATURE_ORDER_LOOKUP = PER_OUTPUT_PORT
    PROCESS_DUPS = NO
    REJECT_NULL_MISSING_KEYS = No
    SUPPLIERS_FIRST = Yes
    ATTR_CONFLICT_RES = Use Requestor
    MERGE_TYPE = Attributes Only
    MERGED -> AttributeCreator_3
Note: AttributeCreator_3 [AttributeCreator Version 9] / Attributes To Create: New AttributeValueRelaticsDataXML<import> / @Value(_file_contents) / </import> / Latest Version: 10
AttributeCreator_3
    ATTR_TABLE:
      SET_TO RelaticsDataXML = <import>
        @Value(_file_contents)
        </import>
    -> TextEncoder_2

Bookmark: 3.3 Relatics Import
Note: Base64 Encoded Import rows
TextEncoder_2
    DEST_ATTR = _encoded
    ENCODING_TYPE = BASE64_ENCODE
    STRING_TO_ENCODE = @Value(RelaticsDataXML)
    -> TextEncoder
Note: Operation as XML (replace & )
TextEncoder
    DEST_ATTR = Operation
    ENCODING_TYPE = XML_ENCODE
    STRING_TO_ENCODE = @Value(Operation)
    -> ParameterFetcher_2
Note: SoapXML
AttributeCreator_2
    ATTR_TABLE:
      SET_TO soapXML = <SOAP-ENV:Envelope xmlns:SOAP-ENV="http://www.w3.org/2003/05/soap-envelope" xmlns:xsi="http://www.w3.org/2001/XMLSchema-instance" xmlns:xsd="http://www.w3.org/2001/XMLSchema">
          <SOAP-ENV:Body>
            <Import xmlns="http://www.relatics.com/">
              <Operation>@Value(Operation)</Operation>
              <Identification>
                <Identification>
                  <Workspace>@Value(RelaticsWorkspace)</Workspace>
                </Identification>
              </Identification>
              <Authentication>
                <Authentication>
                  <Entrycode>@Value(Entrycode)</Entrycode>
                </Authentication>
              </Authentication>
              <Filename>@Value(Filename)</Filename>
              <Data>
              @Value(_encoded)
              </Data>
            </Import>
          </SOAP-ENV:Body>
        </SOAP-ENV:Envelope>
    -> HTTPCaller_7
HTTPCaller_7
    CLIENT_CERTIFICATE_TYPE = NONE
    CONNECTION_TIMEOUT_LENGTH = 3600
    CONTENT_TYPE_LOOKUP = application/soap+xml
    ERROR_ATTR = _error
    FOLLOW_REDIRECTS = FOLLOW_WITH_GET
    HTTP_METHOD = POST
    MAX_HTTP_VERSION = HTTP_2
    MAX_TRANSFERS_IN_PROGRESS = 1
    MINIMUM_ENCRYPTION_LEVEL = OS_DEFAULT
    REDIRECT_AUTH = ORIGINAL_DOMAIN_ONLY
    RESPONSE_HEADER_LIST_ATTR = _response_headers
    RESPONSE_TYPE = Attribute
    RETRY_FAILED_TRANSFERS = CONNECTION 429 500 501 502 503 504 505 506 507 508 509 510 511
    RETRY_INITIAL_BACKOFF = 5000
    RETRY_MAX_RETRIES = 3
    SPLIT_MULTIPART_DOWNLOADS = NO
    STATUS_CODE_ATTR = _http_status_code
    TARGET_ATTR = _response_body
    TARGET_ATTR_ENCODING = auto-detect
    TARGET_URL = $(TARGET_URL)
    TRANSFER_TIMEOUT_LENGTH = 0
    UPLOAD_BODY = @Value(soapXML)
    UPLOAD_TYPE = STRING_UPLOAD
    USE_COOKIES = No
    VERIFY_SSL_CERTIFICATES = Yes
    UPLOAD_CONTENT_TYPE = SOAP XML (application/soap+xml)
    -> StringSearcher
    <REJECTED> -> AttributeRemover
StringSearcher
    CASE = no
    MATCHES_ATTR = _matches
    PRESERVE_FEATURE_ORDER_LOOKUP = PER_OUTPUT_PORT
    REGEXP = Message Time="([\d:]+)" Result="(Progress|Error)">([^<]+)</Message>
    STRING_TO_SEARCH = @Value(_response_body)
    MATCHED -> AttributeKeeper_2
AttributeKeeper_2
    CREATE_BULK_MODE_FEATURES = NO
    KEEP_ATTRS = Filename,Operation
    KEEP_LIST = _matches{}.match
    -> ListExploder
ListExploder
    ATTR_CONFLICT_RES_LOOKUP = INCOMING_IF_CONFLICT
    INDEX_ATTR = _element_index
    LIST_ATTR = _matches{}
    ATTR_ACCUM_MODE = Merge List Attributes
    ATTR_CONFLICT_RES = Use List Attribute Values
    ELEMENTS -> Tester
Tester
    BOOL_OP = OR
    TEST_CLAUSE = CASE_SENSITIVE_TEST @Value(match) NOT_CONTAINS Processing row
    TEST_MODE = CASE_SENSITIVE_TEST
    PASSED -> StringReplacer
StringReplacer
    CASE = NO
    FIND_TEXT = </Message>
    NO_MATCH = _FME_NO_OP_
    REGEXP = NO
    SRC_ATTRS = match
    -> HTMLReportGenerator
HTMLReportGenerator
    CONTENT_LIST = HEADER TABLE
    GROUP_BY = Filename Operation
    PAGE_CONFIG:
      HEADER{{TEXT;Relatics Import: @Value(Operation)
      Filename: @Value(Filename);HEADER;$(HEADER);HEADER_ID;;ALIGNMENT;LEFT;COLOR;0,0,0;FME_CONTROLLER_QUERY_FILE;transformers/dependencies/html5/Header.fme;FME_CONTROLLER_CHOICE;Header}}TABLE{{STYLE;DEFAULT;TABLE;match|Message;FME_CONTROLLER_QUERY_FILE;transformers/dependencies/html5/Table.fme;FME_CONTROLLER_CHOICE;Table}}
    -> StringSearcher_2
StringSearcher_2
    CASE = no
    MATCHED_PARTS_ATTR = submatch
    PRESERVE_FEATURE_ORDER_LOOKUP = PER_OUTPUT_PORT
    REGEXP = (.+)-(\d+)\.xml
    STRING_TO_SEARCH = @Value(Filename)
    MATCHED -> Sorter
Sorter
    SORT_PARM = submatch{0}.part ALPHA ASCENDING submatch{1}.part NUMERIC ASCENDING
    SORTED -> HTMLLayouter_2
HTMLLayouter_2
    DIV_STYLE = NONE
    GROUP_BY = Operation
    LAYOUT = VERTICAL
    TITLE = @Value(Operation)
    -> HTML (writer HTML_1)
HTML (writer HTML_1)
    attributes: html_content buffer
AttributeRemover
    LIST_ATTRS = _feature_types{} attribute{}
    REMOVE_ATTRS = RelaticsDataXML,_dataset,_dirname,_dirpath,_encoded,_extension,_file_contents,_rootname,_timestamp
    -> Logger
Logger
    LOG_FEATURE = LOG_ONLY
    MAXCOORDS = 0
    MAXFEATS = 20
    MESSAGE = Feature is:
    SEVERITY = ERROR
    LOGGED -> Terminator
Terminator
    MESSAGE = Translation Terminated

Bookmark: Request per Relatics Workspace
ParameterFetcher_2
    ATTR_LIST = _RelaticsWorkspace $(RelaticsWorkspace)
    -> AttributeSplitter
AttributeSplitter
    ATTR_NAME = _RelaticsWorkspace
    DELIMITER = ,
    DROP_EMPTY_PARTS = NO
    LIST_NAME = RelaticsWorkspace
    TRIM_TYPE = BOTH
    -> ListExploder_2
ListExploder_2
    ATTR_CONFLICT_RES_LOOKUP = INCOMING_IF_CONFLICT
    INDEX_ATTR = _element_index
    LIST_ATTR = RelaticsWorkspace{}
    ATTR_ACCUM_MODE = Merge List Attributes
    ATTR_CONFLICT_RES = Use List Attribute Values
    ELEMENTS -> AttributeCreator_2

FME custom transformer BatchGrouper

Parameters:
- GROUP_SIZE = 100   # Group/Batch Size
- VAL_ATTR =   # ALLOW_NEW New Group Attribute

Input (input)
    -> Counter
Output (output)

Bookmark: Group/Batch Features Based on Size
Counter
    CNT_ATTR = _groupByCount
    DOMAIN = counter
    SCOPE = Local
    START = 0
    SCOPEVAR = Local
    -> ExpressionEvaluator
ExpressionEvaluator
    ACTION = Create New Attribute
    EXPRESSION = @floor(@Value(_groupByCount)/$(GROUP_SIZE))
    VAL_ATTR = $(VAL_ATTR)
    -> AttributeRemover
AttributeRemover
    REMOVE_ATTRS = _groupByCount
    -> Output (output)
