FME workspace SchedulingBulkRelatics_VS1_NoDiscriminator.fmw
History: 16-05-2025,Anne Jop de Jong,CSV logging toegevoegd

Parameters:
- RUN_UUID:   # Run UUID
      from uuid import uuid4
      
      return str(uuid4())
- VS1_NameExtention =   # VS1 NameExtention
- XLSXR_Source = C:\Users\OscarWillemsAvineon-\OneDrive - Tensing\Documents\Consultancy\TenneT\BulkRelatics\6.0_FME-DynamicConfigurationSheet_VS1-SystemAndProces.xlsx   # Source Excel with SPARQL
- START_QUERY = 1   # Query to start with (based on order)
- REL_ENDPOINT = https://tennet.relaticsonline.com/DataExchange.asmx?wsdl   # Relatics Endpoint
- REL_WORKSPACE = 6799f418-d8e4-4a81-ab20-54eea9336335   # Relatics Workspace
- SERVER_CONNECTION = tennet.vicrea.nl   # "FME Server"% Connection
- BATCH_SIZE_2 = 10000   # " " Batch Size for Relatics
- RELATICS_FIRST_WORKSPACE:   # Scripted Parameter Value
      import fme
      
      workspaces = fme.macroValues['REL_WORKSPACE']
      #print(workspaces)
      list = workspaces.split(',')
      #print(list)
      
      return list[0]
- FME_SHAREDRESOURCE_DATA = D:\OneDrive - Vicrea Solutions B.V\FME Consultancy\TenneT\Development   # FME Flow Data Directory
- FME_SHAREDRESOURCE_TEMP = C:\temp   # FME Flow Temporary Resource Directory

Readers:
- XLSXR_2: XLSXR from $(XLSXR_Source)

Writers:
- XLSXW_2: XLSXW to C:\temp

AttributeCreator
    ATTR_TABLE = SET_TO VS1_NameExtention (buffer) = FME_CONDITIONAL:DEFAULT_VALUE'_FME_NO_OP_'BOOL_OP;OR;COMPOSITE_TEST;1;TEST VS1_NameExtention ATTRIBUTE_HAS_A_VALUE _FME_BLANK_STRING_'@Value(VS1_NameExtention) - 'FME_NUM_CONDITIONS2___
    -> StringReplacer_6
Note: StringReplacer_6 [StringReplacer Version 5] / Attributes: Query / Text To Replace: {{VS1_NameExtention}} / Replacement Text: <2 Possible Values>
StringReplacer_6
    CASE = NO
    FIND_TEXT = {{VS1_NameExtention}}
    NO_MATCH = _FME_NO_OP_
    REGEXP = NO
    REPLACE_TEXT = "@Value(VS1_NameExtention)"
    SRC_ATTRS = Query
    -> Junction
Junction
    -> PythonCaller
    -> DuplicateFilter
Note: Order >= Start_Order
PythonCaller
    PYTHONSOURCE:
      import fme
      from fme import BaseTransformer
      import fmeobjects


      class FeatureProcessor(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def has_support_for(self, support_type: int):
              """This method is called by FME to determine if the PythonCaller supports Bulk mode,
              which allows for significant performance gains when processing large numbers of features.
              """
              return support_type == fmeobjects.FME_SUPPORT_FEATURE_TABLE_SHIM

          def input(self, feature: fmeobjects.FMEFeature):
              """This method is called for each feature which enters the PythonCaller."""
              if int(feature.getAttribute('Order')) >= int(fme.macroValues['START_QUERY']):

                  self.pyoutput(feature, output_tag="PYOUTPUT")
              else:
                  pass
          def close(self):
              """This method is called once all the FME Features have been processed from input()."""
              pass

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              self.pyoutput(feature, output_tag="<Rejected>")
    PYTHONSYMBOL = FeatureProcessor
    -> BinaryEncoder
Note: BUG: Per output port ruins the second record / Workaround: Set to Accross Ports / TestFilter is also broken
Tester_2 [off]
    BOOL_OP = OR
    TEST_CLAUSE = NUM_TEST @Value(Order) >= $(START_QUERY)
    TEST_MODE = NUM_TEST
    PASSED -> BinaryEncoder
BinaryEncoder
    ATTR_TABLE = Query QueryBase64
    ENCODING_TYPE_LOOKUP = BASE64_ENCODE
    ENCODING_TYPE = Base64
    -> AttributeExposer
AttributeExposer
    ATTR_TABLE = QueryBase64,
    -> AttributeCreator_2
AttributeCreator_2
    ATTR_TABLE:
      SET_TO InputJSON (varchar(200)) = {
          "order": @Value(Order),
          "query": "@Value(QueryBase64)",
          "endpoint": "@Value(Endpoint)",
          "filename": "@Value(Filename)",
          "operation": "@Value(Operation)",
          "entrycode": "@Value(Entrycode)"
        }
    -> ImportQuerys (writer XLSXW_2)
    -> AttributeKeeper
    -> DebugLogger
AttributeKeeper
    CREATE_BULK_MODE_FEATURES = NO
    KEEP_ATTRS = InputJSON,Order,REL_WORKSPACE,Operation
    -> Sorter
Sorter
    SORT_PARM = Order NUMERIC ASCENDING
    SORTED -> FMEFlowJobSubmitter_2
FMEFlowJobSubmitter_2
    ACTION = SUBMIT_JOB
    BLOCKING = TRUE
    REPOSITORY = BulkImportRelatics
    SERVER_CONNECTION = $(SERVER_CONNECTION)
    WORKSPACE_NAME = BulkRelatics.fmw
    WORKSPACE_PARAMETERS = InputJSON string @Value(InputJSON) SPARQL_OUTFOLDER string $(FME_SHAREDRESOURCE_TEMP)\$(RUN_UUID) FANOUT_DIR string $(FME_SHAREDRESOURCE_TEMP)\$(RUN_UUID) BATCH_SIZE string $(BATCH_SIZE_2) TARGET_URL string $(REL_ENDPOINT) RelaticsWorkspace string $(REL_WORKSPACE)
    JOB_FAILED -> Junction_2
    <REJECTED> -> Junction_2
Junction_2
    -> Terminator
Terminator
    MESSAGE = Translation Terminated
DebugLogger: Logger [off]
    LOG_FEATURE = NONE
    MAXFEATS = 20
    MESSAGE = Order: @Value(Order), Endpoint: @Value(Endpoint)
    SEVERITY = INFO

Bookmark: Excel Reader
Note: Choice parameter with only ONE choice
ImportQuerys (reader XLSXR_2)
    attributes: Order number(2,0), Query char(6597), Endpoint char(338), Filename char(14), Operation char(34), Entrycode char(13)
    -> Tester
Tester
    BOOL_OP = OR
    TEST_CLAUSE = TEST Query ATTRIBUTE_HAS_A_VALUE ""
    TEST_MODE = TEST
    PASSED -> ParameterFetcher
ParameterFetcher
    ATTR_LIST = REL_ENDPOINT $(REL_ENDPOINT) REL_WORKSPACE $(REL_WORKSPACE) VS1_NameExtention $(VS1_NameExtention)
    -> NullAttributeMapper

Bookmark: Goed zetten discriminatoren
NullAttributeMapper
    ATTRCHOICE_ACTION = SELECTED
    ATTRLIST = VS1_NameExtention
    NULL_TREATMENT_LU = EMPTY
    SOURCE_ATTR_VAL_LU = SETNULL EMPTY MISSINGATTR
    ATTRCHOICE = Selected Attributes
    NULL_TREATMENT = Empty String
    SOURCE_ATTR_VAL = Null Empty "Missing (Selected Attributes Only)"
    -> AttributeCreator

Bookmark: Excel bestand zoals gebruikt
DuplicateFilter
    INPUT_ORDERED_CHOICE_LOOKUP = NO
    KEYATTR = REL_ENDPOINT REL_WORKSPACE VS1_NameExtention
    INPUT_ORDERED_CHOICE = No
    UNIQUE -> RuntimeVariable (writer XLSXW_2)
RuntimeVariable (writer XLSXW_2)
    attributes: REL_ENDPOINT string(20), REL_WORKSPACE string(20), VS2_DISCRIMINATOR string(20)
ImportQuerys (writer XLSXW_2)
    attributes: Order number(2), Query string(50), Endpoint string(50), Filename string(14), Operation string(34), Entrycode string(13), InputJSON string(50)
