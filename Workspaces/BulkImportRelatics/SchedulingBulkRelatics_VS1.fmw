FME workspace SchedulingBulkRelatics_VS1.fmw

Parameters:
- RUN_UUID:   # Run UUID
      from uuid import uuid4
      
      return str(uuid4())
- VS1_NameExtention =   # VS1 NameExtention
- VS1_discriminator_value_TypeVoltageLevel = {N.v.t.}
- VS1_discriminator_value_TypeInsulation = {N.v.t.}   # VS1 Discriminator TypeInsulation
- VS1_discriminator_value_TypeNoodstroomaggregaat = {N.v.t.}   # Category 1,{Category 1}%Category 2,{Category 2}%N.v.t.,{N.v.t.} VS1 Discriminator TypeNoodstroomaggregaat
- VS1_discriminator_value_TypeSecurity = {N.v.t.}   # Category A,{Category A}%Category B,{Category B}%N.v.t.,{N.v.t.} VS1 Discriminator TypeSecurity
- XLSXR_Source = C:\Users\willemo\Downloads\6.0_FME-DynamicConfigurationSheet_VS1-SystemAndProces.xlsx   # Source Excel with SPARQL
- START_QUERY = 1   # Query to start with (based on order)
- REL_ENDPOINT = https://tennet.relaticsonline.com/DataExchange.asmx?wsdl   # Relatics Endpoint
- REL_WORKSPACE = 6799f418-d8e4-4a81-ab20-54eea9336335   # Relatics Workspace
- RELATICS_FIRST_WORKSPACE:   # Scripted Parameter Value
      import fme
      
      workspaces = fme.macroValues['REL_WORKSPACE']
      #print(workspaces)
      list = workspaces.split(',')
      #print(list)
      
      return list[0]
- SERVER_CONNECTION = tennet.vicrea.nl   # "FME Server"% Connection
- BATCH_SIZE_2 = 10000   # " " Batch Size for Relatics
- FME_SHAREDRESOURCE_DATA = D:\OneDrive - Vicrea Solutions B.V\FME Consultancy\TenneT\Development   # FME Flow Data Directory
- FME_SHAREDRESOURCE_TEMP = C:\temp   # FME Flow Temporary Resource Directory

Readers:
- XLSXR_1: XLSXR from $(XLSXR_Source)

Writers:
- XLSXW_1: XLSXW to C:\temp

AttributeCreator
    ATTR_TABLE = SET_TO VS1_NameExtention = FME_CONDITIONAL:DEFAULT_VALUE'_FME_NO_OP_'BOOL_OP;OR;COMPOSITE_TEST;1;TEST VS1_NameExtention ATTRIBUTE_HAS_A_VALUE _FME_BLANK_STRING_'@Value(VS1_NameExtention) - 'FME_NUM_CONDITIONS2___
    -> StringReplacer_6
Note: StringReplacer_6 [StringReplacer Version 5] / Attributes: Query / Text To Replace: {{VS1_NameExtention}} / Replacement Text: <2 Possible Values>
StringReplacer_6
    CASE = NO
    FIND_TEXT = {{VS1_NameExtention}}
    NO_MATCH = _FME_NO_OP_
    REGEXP = NO
    REPLACE_TEXT = "@Value(VS1_NameExtention)"
    SRC_ATTRS = Query
    -> Tester_3
Tester_6
    BOOL_OP = OR
    TEST_CLAUSE = CASE_INSENSITIVE_TEST @Value(VS1_discriminator_value_TypeSecurity) CONTAINS N.v.t.
    TEST_MODE = CASE_INSENSITIVE_TEST
    PASSED -> StringSearcher_4
    FAILED -> StringReplacer_16
Note: Search block of Discriminator
StringSearcher_4
    CASE = no
    MATCHED_RESULT_ATTR = SecurityPart
    PRESERVE_FEATURE_ORDER_LOOKUP = PER_OUTPUT_PORT
    REGEXP = ##########DISCRIMINATOR---4: Security type.+##########DISCRIMINATOR---4: Security type
    STRING_TO_SEARCH = @Value(Query)
    MATCHED -> AttributeCopier_4
    NOT_MATCHED -> StringReplacer_16
AttributeCopier_4
    ATTR_TABLE = COPY SecurityPart > SecurityPartOriginal
    MISSING_INPUT_ATTRS = REMOVE
    -> StringReplacer_17
Note: Add # to each line of replacement text
StringReplacer_17
    CASE = NO
    FIND_TEXT = ^
    NO_MATCH = _FME_NO_OP_
    REGEXP = YES
    REPLACE_TEXT = #
    SRC_ATTRS = SecurityPart
    -> StringReplacer_18
Note: Replace original part with commented part
StringReplacer_18
    CASE = NO
    FIND_TEXT = @Value(SecurityPartOriginal)
    NO_MATCH = _FME_NO_OP_
    REGEXP = NO
    REPLACE_TEXT = @Value(SecurityPart)
    SRC_ATTRS = VoltagLevelPart,Query
    -> StringReplacer_16
Note: {{VS1_discriminator_value_TypeSecurity}}
StringReplacer_16
    CASE = NO
    FIND_TEXT = {{VS1_discriminator_value_TypeSecurity}}
    NO_MATCH = _FME_NO_OP_
    REGEXP = NO
    REPLACE_TEXT = @Value(VS1_discriminator_value_TypeSecurity)
    SRC_ATTRS = Query
    -> Junction
Junction
    -> DuplicateFilter
    -> PythonCaller
PythonCaller
    PYTHONSOURCE:
      import fme
      from fme import BaseTransformer
      import fmeobjects


      class FeatureProcessor(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def has_support_for(self, support_type: int):
              """This method is called by FME to determine if the PythonCaller supports Bulk mode,
              which allows for significant performance gains when processing large numbers of features.
              """
              return support_type == fmeobjects.FME_SUPPORT_FEATURE_TABLE_SHIM

          def input(self, feature: fmeobjects.FMEFeature):
              """This method is called for each feature which enters the PythonCaller."""
              if int(feature.getAttribute('Order')) >= int(fme.macroValues['START_QUERY']):

                  self.pyoutput(feature, output_tag="PYOUTPUT")
              else:
                  pass
          def close(self):
              """This method is called once all the FME Features have been processed from input()."""
              pass

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              self.pyoutput(feature, output_tag="<Rejected>")
    PYTHONSYMBOL = FeatureProcessor
    -> ImportQuerys (writer XLSXW_1)
    -> Sorter
Sorter
    SORT_PARM = Order NUMERIC ASCENDING
    SORTED -> BinaryEncoder
BinaryEncoder
    ATTR_TABLE = Query QueryBase64
    ENCODING_TYPE_LOOKUP = BASE64_ENCODE
    ENCODING_TYPE = Base64
    -> JSONTemplater [ROOT]
Note: { / "order": fme:get-attribute("Order"), / "query": fme:get-attribute("QueryBase64"), / "endpoint": fme:get-attribute("Endpoint"), / "filename": fme:get-attribute("Filename"), / "operation": fme:get-attribute("Operation"), / "entrycode": fme:get-attribute("Entrycode") / }
JSONTemplater
    RESULT_ATTRIBUTE = InputJSON
    ROOT_QUERY_EXPR:
      {
        "order": fme:get-attribute("Order"),
        "query": fme:get-attribute("QueryBase64"),
        "endpoint": fme:get-attribute("Endpoint"),
        "filename": fme:get-attribute("Filename"),
        "operation": fme:get-attribute("Operation"),
        "entrycode": fme:get-attribute("Entrycode")
      }
    VISIBLE_QUERY_VALIDATE = Yes
    -> FMEServerJobSubmitter_2
FMEServerJobSubmitter_2
    ACTION = SUBMIT_JOB
    BLOCKING = TRUE
    REPOSITORY = BulkImportRelatics
    SERVER_CONNECTION = $(SERVER_CONNECTION)
    WORKSPACE_NAME = BulkRelatics.fmw
    WORKSPACE_PARAMETERS = InputJSON string @Value(InputJSON) SPARQL_OUTFOLDER string $(FME_SHAREDRESOURCE_TEMP)\$(RUN_UUID) FANOUT_DIR string $(FME_SHAREDRESOURCE_TEMP)\$(RUN_UUID) BATCH_SIZE string $(BATCH_SIZE_2) TARGET_URL string $(REL_ENDPOINT) RelaticsWorkspace string $(REL_WORKSPACE)
    JOB_FAILED -> Junction_2
    <REJECTED> -> Junction_2
Junction_2
    -> Terminator
Terminator
    MESSAGE = Translation Terminated

Bookmark: Excel Reader
Note: Choice parameter with only ONE choice
ImportQuerys (reader XLSXR_1)
    attributes: Order number(2,0), Query char(6597), Endpoint char(338), Filename char(14), Operation char(34), Entrycode char(13)
    -> Tester
Tester
    BOOL_OP = OR
    TEST_CLAUSE = TEST Query ATTRIBUTE_HAS_A_VALUE ""
    TEST_MODE = TEST
    PASSED -> ParameterFetcher
ParameterFetcher
    ATTR_LIST = REL_ENDPOINT $(REL_ENDPOINT) REL_WORKSPACE $(REL_WORKSPACE) VS1_NameExtention $(VS1_NameExtention) VS1_discriminator_value_TypeInsulation $(VS1_discriminator_value_TypeInsulation) VS1_discriminator_value_TypeNoodstroomaggregaat $(VS1_discriminator_value_TypeNoodstroomaggregaat) VS1_discriminator_value_TypeSecurity $(VS1_discriminator_value_TypeSecurity) VS1_discriminator_value_TypeVoltageLevel $(VS1_discriminator_value_TypeVoltageLevel)
    -> NullAttributeMapper

Bookmark: Goed zetten discriminatoren
NullAttributeMapper
    ATTRCHOICE_ACTION = SELECTED
    ATTRLIST = VS1_discriminator_value_TypeInsulation VS1_discriminator_value_TypeNoodstroomaggregaat VS1_discriminator_value_TypeSecurity VS1_discriminator_value_TypeVoltageLevel VS1_NameExtention
    NULL_TREATMENT_LU = EMPTY
    SOURCE_ATTR_VAL_LU = SETNULL EMPTY MISSINGATTR
    ATTRCHOICE = Selected Attributes
    NULL_TREATMENT = Empty String
    SOURCE_ATTR_VAL = Null Empty "Missing (Selected Attributes Only)"
    -> StringReplacer_2
StringReplacer_2
    CASE = NO
    FIND_TEXT = {|}
    NO_MATCH = _FME_NO_OP_
    REGEXP = YES
    REPLACE_TEXT = "
    SRC_ATTRS = VS1_discriminator_value_TypeInsulation,VS1_discriminator_value_TypeNoodstroomaggregaat,VS1_discriminator_value_TypeSecurity,VS1_discriminator_value_TypeVoltageLevel
    -> StringReplacer_7
StringReplacer_7
    CASE = NO
    FIND_TEXT = "+
    NO_MATCH = _FME_NO_OP_
    REGEXP = YES
    REPLACE_TEXT = "
    SRC_ATTRS = VS1_discriminator_value_TypeInsulation,VS1_discriminator_value_TypeNoodstroomaggregaat,VS1_discriminator_value_TypeSecurity,VS1_discriminator_value_TypeVoltageLevel
    -> AttributeCreator

Bookmark: {{VS1_discriminator_value_TypeVoltageLevel}}
Tester_3
    BOOL_OP = OR
    TEST_CLAUSE = CASE_INSENSITIVE_TEST @Value(VS1_discriminator_value_TypeVoltageLevel) CONTAINS N.v.t.
    TEST_MODE = CASE_INSENSITIVE_TEST
    PASSED -> StringSearcher
    FAILED -> StringReplacer
Note: Search block of Discriminator
StringSearcher
    CASE = no
    MATCHED_RESULT_ATTR = VoltagLevelPart
    PRESERVE_FEATURE_ORDER_LOOKUP = PER_OUTPUT_PORT
    REGEXP = ##########DISCRIMINATOR---1: Voltage type.+##########DISCRIMINATOR---1: Voltage type
    STRING_TO_SEARCH = @Value(Query)
    MATCHED -> AttributeCopier
    NOT_MATCHED -> StringReplacer
AttributeCopier
    ATTR_TABLE = COPY VoltagLevelPart > VoltagLevelPartOriginal
    MISSING_INPUT_ATTRS = REMOVE
    -> StringReplacer_9
Note: Add # to each line of replacement text
StringReplacer_9
    CASE = NO
    FIND_TEXT = ^
    NO_MATCH = _FME_NO_OP_
    REGEXP = YES
    REPLACE_TEXT = #
    SRC_ATTRS = VoltagLevelPart
    -> StringReplacer_10
Note: Replace original part with commented part
StringReplacer_10
    CASE = NO
    FIND_TEXT = @Value(VoltagLevelPartOriginal)
    NO_MATCH = _FME_NO_OP_
    REGEXP = NO
    REPLACE_TEXT = @Value(VoltagLevelPart)
    SRC_ATTRS = Query
    -> StringReplacer
Note: {{VS1_discriminator_value_TypeVoltageLevel}}
StringReplacer
    CASE = NO
    FIND_TEXT = {{VS1_discriminator_value_TypeVoltageLevel}}
    NO_MATCH = _FME_NO_OP_
    REGEXP = NO
    REPLACE_TEXT = @Value(VS1_discriminator_value_TypeVoltageLevel)
    SRC_ATTRS = Query
    -> Tester_4

Bookmark: {{VS1_discriminator_value_TypeInsulation}}
Tester_4
    BOOL_OP = OR
    TEST_CLAUSE = CASE_INSENSITIVE_TEST @Value(VS1_discriminator_value_TypeInsulation) CONTAINS N.v.t.
    TEST_MODE = CASE_INSENSITIVE_TEST
    PASSED -> StringSearcher_2
    FAILED -> StringReplacer_8
Note: Search block of Discriminator
StringSearcher_2
    CASE = no
    MATCHED_RESULT_ATTR = InsulationPart
    PRESERVE_FEATURE_ORDER_LOOKUP = PER_OUTPUT_PORT
    REGEXP = ##########DISCRIMINATOR---2: Insulation type.+##########DISCRIMINATOR---2: Insulation type
    STRING_TO_SEARCH = @Value(Query)
    MATCHED -> AttributeCopier_2
    NOT_MATCHED -> StringReplacer_8
AttributeCopier_2
    ATTR_TABLE = COPY InsulationPart > InsulationPartOriginal
    MISSING_INPUT_ATTRS = REMOVE
    -> StringReplacer_11
Note: Add # to each line of replacement text
StringReplacer_11
    CASE = NO
    FIND_TEXT = ^
    NO_MATCH = _FME_NO_OP_
    REGEXP = YES
    REPLACE_TEXT = #
    SRC_ATTRS = InsulationPart
    -> StringReplacer_12
Note: Replace original part with commented part
StringReplacer_12
    CASE = NO
    FIND_TEXT = @Value(InsulationPartOriginal)
    NO_MATCH = _FME_NO_OP_
    REGEXP = NO
    REPLACE_TEXT = @Value(InsulationPart)
    SRC_ATTRS = Query
    -> StringReplacer_8
Note: {{VS1_discriminator_value_TypeInsulation}}
StringReplacer_8
    CASE = NO
    FIND_TEXT = {{VS1_discriminator_value_TypeInsulation}}
    NO_MATCH = _FME_NO_OP_
    REGEXP = NO
    REPLACE_TEXT = @Value(VS1_discriminator_value_TypeInsulation)
    SRC_ATTRS = Query
    -> Tester_5

Bookmark: {{VS1_discriminator_value_TypeNoodstroomaggregaat}}
Tester_5
    BOOL_OP = OR
    TEST_CLAUSE = CASE_INSENSITIVE_TEST @Value(VS1_discriminator_value_TypeNoodstroomaggregaat) CONTAINS N.v.t.
    TEST_MODE = CASE_INSENSITIVE_TEST
    PASSED -> StringSearcher_3
    FAILED -> StringReplacer_13
Note: Search block of Discriminator
StringSearcher_3
    CASE = no
    MATCHED_RESULT_ATTR = NoodstroomaggregaatPart
    PRESERVE_FEATURE_ORDER_LOOKUP = PER_OUTPUT_PORT
    REGEXP = ##########DISCRIMINATOR---3: Noodstroomaggregaat type.+##########DISCRIMINATOR---3: Noodstroomaggregaat type
    STRING_TO_SEARCH = @Value(Query)
    MATCHED -> AttributeCopier_3
    NOT_MATCHED -> StringReplacer_13
AttributeCopier_3
    ATTR_TABLE = COPY NoodstroomaggregaatPart > NoodstroomaggregaatPartOriginal
    MISSING_INPUT_ATTRS = REMOVE
    -> StringReplacer_14
Note: Add # to each line of replacement text
StringReplacer_14
    CASE = NO
    FIND_TEXT = ^
    NO_MATCH = _FME_NO_OP_
    REGEXP = YES
    REPLACE_TEXT = #
    SRC_ATTRS = NoodstroomaggregaatPart
    -> StringReplacer_15
Note: Replace original part with commented part
StringReplacer_15
    CASE = NO
    FIND_TEXT = @Value(NoodstroomaggregaatPartOriginal)
    NO_MATCH = _FME_NO_OP_
    REGEXP = NO
    REPLACE_TEXT = @Value(NoodstroomaggregaatPart)
    SRC_ATTRS = Query
    -> StringReplacer_13
Note: {{VS1_discriminator_value_TypeNoodstroomaggregaat}}
StringReplacer_13
    CASE = NO
    FIND_TEXT = {{VS1_discriminator_value_TypeNoodstroomaggregaat}}
    NO_MATCH = _FME_NO_OP_
    REGEXP = NO
    REPLACE_TEXT = @Value(VS1_discriminator_value_TypeNoodstroomaggregaat)
    SRC_ATTRS = Query
    -> Tester_6

Bookmark: Excel bestand zoals gebruikt
DuplicateFilter
    INPUT_ORDERED_CHOICE_LOOKUP = NO
    KEYATTR = REL_ENDPOINT REL_WORKSPACE VS1_discriminator_value_TypeInsulation VS1_discriminator_value_TypeNoodstroomaggregaat VS1_discriminator_value_TypeSecurity VS1_discriminator_value_TypeVoltageLevel VS1_NameExtention
    PRESERVE_FEATURE_ORDER_LOOKUP = PER_OUTPUT_PORT
    INPUT_ORDERED_CHOICE = No
    UNIQUE -> RuntimeVariable (writer XLSXW_1)
RuntimeVariable (writer XLSXW_1)
    attributes: REL_ENDPOINT string(20), REL_WORKSPACE string(20), VS2_DISCRIMINATOR string(20)
ImportQuerys (writer XLSXW_1)
    attributes: Order number(2), Query string(6597), Endpoint string(338), Filename string(14), Operation string(34), Entrycode string(13)
