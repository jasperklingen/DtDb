FME workspace SchedulingBulkRelatics_VS2.fmw

Parameters:
- VS2_discriminator = {Algemeen} {Stations}   # Algemeen VS2,{Algemeen}%Lijnen VS2,{Lijnen}%Stations VS2,{Stations}%Kabels VS2,{Kabels}%BRP VS2,{BRP} VS2 discriminator
- XLSXR_Source = C:\Users\AnneJopdeJongTensing\OneDrive - Tensing\Documenten\Tennet\InputData\8.0_FME-DynamicConfigurationSheet_VS2.xlsx   # Source Excel with SPARQL
- START_QUERY = 2   # Query to start with (based on order)
- REL_ENDPOINT = https://tennet.relaticsonline.com/DataExchange.asmx?wsdl   # Relatics Endpoint
- REL_WORKSPACE = 6799f418-d8e4-4a81-ab20-54eea9336335   # Relatics Workspace
- RUN_UUID:   # Run UUID
      from uuid import uuid4
      
      return str(uuid4())
- SERVER_CONNECTION = annejopdejongtensing FME Flow   # "FME Server"% Connection
- BATCH_SIZE_2 = 10000   # " " Batch Size for Relatics
- FME_SHAREDRESOURCE_DATA = D:\OneDrive - Vicrea Solutions B.V\FME Consultancy\TenneT\Development   # FME Flow Data Directory
- FME_SHAREDRESOURCE_TEMP = C:\temp   # FME Flow Temporary Resource Directory

Readers:
- XLSXR_1: XLSXR from $(XLSXR_Source)

Writers:
- XLSXW_1: XLSXW to $(FME_SHAREDRESOURCE_TEMP)

Note: Aanpassen van ## naar {{VS2_DISCRIMINATOR}} / Choice parameters met multiple / VALUES ?projectCategory {"Algemeen" "Station" }
PythonCaller
    PYTHONSOURCE:
      import fme
      from fme import BaseTransformer
      import fmeobjects


      class FeatureProcessor(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def has_support_for(self, support_type: int):
              """This method is called by FME to determine if the PythonCaller supports Bulk mode,
              which allows for significant performance gains when processing large numbers of features.
              """
              return support_type == fmeobjects.FME_SUPPORT_FEATURE_TABLE_SHIM

          def input(self, feature: fmeobjects.FMEFeature):
              """This method is called for each feature which enters the PythonCaller."""
              if int(feature.getAttribute('Order')) >= int(fme.macroValues['START_QUERY']):

                  self.pyoutput(feature, output_tag="PYOUTPUT")
              else:
                  pass
          def close(self):
              """This method is called once all the FME Features have been processed from input()."""
              pass

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              self.pyoutput(feature, output_tag="<Rejected>")
    PYTHONSYMBOL = FeatureProcessor
    -> ImportQuerys (writer XLSXW_1)
    -> Sorter
Sorter
    SORT_PARM = Order NUMERIC ASCENDING
    SORTED -> BinaryEncoder
BinaryEncoder
    ATTR_TABLE = Query QueryBase64
    ENCODING_TYPE_LOOKUP = BASE64_ENCODE
    ENCODING_TYPE = Base64
    -> JSONTemplater [ROOT]
Note: { / "order": fme:get-attribute("Order"), / "query": fme:get-attribute("QueryBase64"), / "endpoint": fme:get-attribute("Endpoint"), / "filename": fme:get-attribute("Filename"), / "operation": fme:get-attribute("Operation"), / "entrycode": fme:get-attribute("Entrycode") / }
JSONTemplater
    RESULT_ATTRIBUTE = InputJSON
    ROOT_QUERY_EXPR:
      {
        "order": fme:get-attribute("Order"),
        "query": fme:get-attribute("QueryBase64"),
        "endpoint": fme:get-attribute("Endpoint"),
        "filename": fme:get-attribute("Filename"),
        "operation": fme:get-attribute("Operation"),
        "entrycode": fme:get-attribute("Entrycode")
      }
    VISIBLE_QUERY_VALIDATE = Yes
    -> FMEServerJobSubmitter_2
FMEServerJobSubmitter_2
    ACTION = SUBMIT_JOB
    BLOCKING = TRUE
    REPOSITORY = BulkImportRelatics
    SERVER_CONNECTION = $(SERVER_CONNECTION)
    WORKSPACE_NAME = BulkRelatics.fmw
    WORKSPACE_PARAMETERS = InputJSON string @Value(InputJSON) SPARQL_OUTFOLDER string $(FME_SHAREDRESOURCE_TEMP)\$(RUN_UUID) FANOUT_DIR string $(FME_SHAREDRESOURCE_TEMP)\$(RUN_UUID) BATCH_SIZE string $(BATCH_SIZE_2) TARGET_URL string $(REL_ENDPOINT) RelaticsWorkspace string $(REL_WORKSPACE)
    JOB_FAILED -> Junction_2
    <REJECTED> -> Junction_2
Junction_2
    -> Terminator
Terminator
    MESSAGE = Translation Terminated

Bookmark: Excel Reader
ImportQuerys (reader XLSXR_1)
    attributes: Order number(2,0), Query char(6597), Endpoint char(338), Filename char(14), Operation char(34), Entrycode char(13)
    -> Tester
Tester
    BOOL_OP = OR
    TEST_CLAUSE = TEST Query ATTRIBUTE_HAS_A_VALUE ""
    TEST_MODE = TEST
    PASSED -> ParameterFetcher
ParameterFetcher
    ATTR_LIST = VS2_DISCRIMINATOR $(VS2_discriminator) REL_ENDPOINT $(REL_ENDPOINT) REL_WORKSPACE $(REL_WORKSPACE)
    -> StringReplacer_2
StringReplacer_2
    CASE = NO
    FIND_TEXT = {|}
    NO_MATCH = _FME_NO_OP_
    REGEXP = YES
    REPLACE_TEXT = "
    SRC_ATTRS = VS2_DISCRIMINATOR
    -> StringReplacer
Note: {{VS2_discriminator}}
StringReplacer
    CASE = NO
    FIND_TEXT = {{VS2_discriminator}}
    NO_MATCH = _FME_NO_OP_
    REGEXP = NO
    REPLACE_TEXT = @Value(VS2_DISCRIMINATOR)
    SRC_ATTRS = Query
    -> PythonCaller
    -> DuplicateFilter

Bookmark: Excel bestand zoals gebruikt
DuplicateFilter
    INPUT_ORDERED_CHOICE_LOOKUP = NO
    KEYATTR = REL_ENDPOINT REL_WORKSPACE VS2_DISCRIMINATOR
    PRESERVE_FEATURE_ORDER_LOOKUP = PER_OUTPUT_PORT
    INPUT_ORDERED_CHOICE = No
    UNIQUE -> RuntimeVariable (writer XLSXW_1)
RuntimeVariable (writer XLSXW_1)
    attributes: REL_ENDPOINT string(20), REL_WORKSPACE string(20), VS2_DISCRIMINATOR string(20)
ImportQuerys (writer XLSXW_1)
    attributes: Order number(2), Query string(6597), Endpoint string(338), Filename string(14), Operation string(34), Entrycode string(13)
