FME workspace ShoppingCart.fmw
Title: SetupTreeview

Parameters:
- RelaticsWorkspace = d   # Relatics Workspace
- HTML_TEMPLATE = $(FME_SHAREDRESOURCE_DATA)/ShoppingCart/ShoppingCart.html   # Path to html shoppingcart template
- MaxJobRuntime = 1   # Maximum time in seconds child jobs run
- CONFIG = SOV   # Config Name (without .xlsx)
- BatchSize = 1000   # Batch Size for Relatics (0 for no batch)
- FME_SERVER_TOKEN =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   # Enter a Password
- FME_JOB_ID = 12221   # FME Flow Job ID

Writers:
- HTML_1: HTML to Tree.html

Bookmark: Query voor het ophalen van de tree
Creator_2
    GEOMTYPE = Geometry Object
    NUM = 1
    CREATED -> FeatureReader [INITIATOR]
Note: $(FME_SHAREDRESOURCE_DATA)\SOV\Config\$(CONFIG).xlsx
FeatureReader
    ATTRS_TO_EXPOSE = Entrycode Filename Operation Order Query QueryEndpoint QueryName
    ATTR_ACCUM_MODE = Only Use Result
    CLIP_TO_ENVELOPE = NO
    COMBINE_GEOM = Use Result
    DATASET = $(FME_SHAREDRESOURCE_DATA)\SOV\Config\$(CONFIG).xlsx
    FEATURETYPES = SOVQuerys
    FORMAT = XLSXR
    INITIATOR_FIRST_OUTPUT = default
    INTERACT = NONE
    ORDER_RESULTS = No
    OUTPUT_ADD_SCHEMA_ATTRIBUTES = NO
    OUTPUT_FEATURES_DISPLAY = Schema and Data Features
    XLSXR_ALLOW_DOLLAR_SIGNS = YES
    XLSXR_APPLY_FILTERS = No
    XLSXR_CASE_SENSITIVE_FEATURE_TYPES = YES
    XLSXR_CONFIGURATION_DATASET = $(FME_MF_DIR)SOV\Config\SOV.xlsx
    XLSXR_CREATE_FEATURE_TABLES_FROM_DATA = Yes
    XLSXR_EXCEL_COL_NAMES = YES
    XLSXR_EXPANDED_DATES_SCANNING = No
    XLSXR_EXPAND_MERGED_CELLS = Yes
    XLSXR_FORCE_DATETIME = NO
    XLSXR_QUERY_FEATURE_TYPES_FOR_MERGE_FILTERS = Yes
    XLSXR_READ_BLANK_AS = Null
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA = SOVQuerys,0,Order,number,2,0,,1,Query,char,2529,,,2,QueryName,char,28,,,3,QueryEndpoint,char,79,,,4,Filename,char,74,,,5,Operation,char,70,,,6,Entrycode,char,32,,,1,,,,NO,NO,1,C:\Users\OscarWillemsAvineon-\Downloads\SOV\Config\SOV.xlsx,"0,0,6,18",Sheet1,NO,NO
    XLSXR_SCHEMA_HANDLING_REVISION = 2
    XLSXR_SKIP_EMPTY_ROWS = YES
    XLSXR_STRIP_SHEETNAME_SPACES = YES
    XLSXR_TABLELIST = SOVQuerys
    XLSXR_TRIM_ATTR_NAME_WHITESPACE = Yes
    XLSXR_USE_CUSTOM_SCHEMA = NO
    <OTHER> -> Tester
Tester
    BOOL_OP = OR
    TEST_CLAUSE = TEST @Value(QueryName) = Tree
    TEST_MODE = TEST
    PASSED -> Sampler
Sampler
    MODE = ORIGINAL
    RATE = 1
    SAMPLE_TYPE_MULTIPLIER = -1
    SAMPLE_MODE = No
    SAMPLE_TYPE_LONG = First N Features
    SAMPLED -> AttributeKeeper
AttributeKeeper
    CREATE_BULK_MODE_FEATURES = NO
    KEEP_ATTRS = Query,QueryEndpoint
    -> AC_Query
AC_Query: AttributeCreator
    ATTR_TABLE = SET_TO query (buffer) = @Value(Query)
    -> HTTPCaller

Bookmark: Tree ophalen
HTTPCaller
    AUTH_METHOD_TYPE = NC
    AUTH_NAMED_CONNECTION = TenneT Laces
    CLIENT_CERTIFICATE_TYPE = NONE
    CONNECTION_TIMEOUT_LENGTH = 60
    CONTENT_TYPE_LOOKUP = application/sparql-query
    CUSTOM_HEADERS = Accept;application/json Accept-Charset;gzip,deflate,br
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(QueryEndpoint)
    TRANSFER_TIMEOUT_LENGTH = 90
    UPLOAD_BODY = @Value(query)
    UPLOAD_TYPE = STRING_UPLOAD
    USE_COOKIES = No
    VERIFY_SSL_CERTIFICATES = No
    AUTH_METHOD = Web Connection
    UPLOAD_CONTENT_TYPE = application/sparql-query
    -> JSONFragmenter
JSONFragmenter
    EXPLODE_FORMAT = JSON
    EXTRACT_ATTR = Yes
    JSON_ATTR = _response_body
    JSON_QUERY = json[*]["bindings"][*]
    READ_FROM_FILE = NO
    RECURSIVE = YES
    REJECT_EMPTY_LISTS = YES
    FRAGMENTS -> AttributeExposer

Bookmark: Maken tabel van tree
AttributeExposer
    ATTR_TABLE = child.value,varchar(61),childName.value,varchar(108),parent.value,varchar(61),parentName.value,varchar(108),childType.value,varchar(200),parentType.value,varchar(200)
    -> BulkAttributeRenamer
BulkAttributeRenamer
    ATTRCHOICE_ACTION = SELECTED
    ATTRLIST = child.value childName.value childType.value parent.value parentName.value parentType.value
    CASE_DISP = YES
    MODE_CHOICE = RENAME
    PATTERN_ACTION_DISP = REMOVESUFFIX
    REPLACE_STR = .value
    ATTRCHOICE = Selected Attributes
    -> InlineQuerier [Relations]
InlineQuerier
    QUERY_DEF:
      Tree,WITH RECURSIVE Tree AS (
        -- Start with root nodes (parents that are not children)
        SELECT
          r."parent" AS rootUri,
          r."parentName" AS rootLabel,
          r."child",
          r."childName",
          1 AS depth,
          r."parentName" <pipe><pipe> '<pipe> ' <pipe><pipe> r."childName" AS path
        FROM relations r
        WHERE r."parent" NOT IN (SELECT "child" FROM relations)

        UNION ALL

        -- Recursive step: join with children
        SELECT
          t.rootUri,
          t.rootLabel,
          r."child",
          r."childName",
          t.depth + 1 AS depth,
          t.path <pipe><pipe> '<pipe> ' <pipe><pipe> r."childName" AS path
        FROM Tree t
        JOIN relations r ON t."child" = r."parent"
      )

      SELECT * FROM Tree
      ORDER BY rootUri, depth;,FIRST
    QUERY_SCHEMA = Tree,rootUri,varchar(61),rootLabel,varchar(108),child,varchar(61),childName,varchar(108),depth,,path,
    TABLE_DEF = Relations,child,varchar(61),childName,varchar(108),childType,varchar(46),parent,varchar(61),parentName,varchar(108),parentType,varchar(46)
    Tree -> StringConcatenator

Bookmark: Maken CSV van tabel
StringConcatenator
    ACTION = Create New Attribute
    PARM_LINE = fme_basicstring:13%1%12:@Value(child),@Value(path)
    VAL_ATTR = _result
    -> Sorter
Sorter
    SORT_PARM = path ALPHA ASCENDING
    SORTED -> Aggregator
Aggregator
    ACCUM_ATTRS = None
    AGGREGATE_TYPE = Homogeneous Collection (If Possible)
    CONCAT_ATTRS = _result
    MODE = Geometry - Assemble One Level
    SEP = "\n"
    AGGREGATE -> AC_header_CSV

Bookmark: HTML pagina maken, CSV tree in de HTML pluggen
AC_header_CSV: AttributeCreator
    ATTR_TABLE:
      SET_TO csv (varchar(200)) = child,path
        @Value(_result)
    -> PythonCaller
PythonCaller
    NEW_ATTRIBUTES = html_content buffer _html_missing buffer
    PYTHONSOURCE:
      import fme
      import fmeobjects
      import re
      import html as html_lib

      PARAM_PATTERN = re.compile(r"\$\(([^)]+)\)")      # $(FME_JOB_ID), $(MY_PARAM)
      ATTR_PATTERN = re.compile(r"@Value\(([^)]+)\)")    # @Value(attr_name)

      OUTPUT_ATTR = "html_content"
      ESCAPE_VALUES = False


      class FeatureProcessor(object):
          def __init__(self):
              path = fme.macroValues["HTML_TEMPLATE"].strip().strip('"').strip("'")
              with open(path, "r", encoding="utf-8") as f:
                  template = f.read()

              # Parameters are the same for every feature, so resolve them once
              self.missing_params = []

              def fill_param(match):
                  name = match.group(1).strip()
                  value = fme.macroValues.get(name)
                  if value is None:
                      self.missing_params.append(name)
                      return ""
                  return str(value)

              self.template = PARAM_PATTERN.sub(fill_param, template)

          def input(self, feature):
              missing = list(self.missing_params)

              def fill_attr(match):
                  name = match.group(1).strip()
                  value = feature.getAttribute(name)
                  if value is None:
                      missing.append(name)
                      return ""
                  value = str(value)
                  return html_lib.escape(value) if ESCAPE_VALUES else value

              feature.setAttribute(OUTPUT_ATTR, ATTR_PATTERN.sub(fill_attr, self.template))

              if missing:
                  feature.setAttribute("_html_missing", ",".join(sorted(set(missing))))
              self.pyoutput(feature)

          def close(self):
              pass
    PYTHONSYMBOL = FeatureProcessor
    -> HTML (writer HTML_1)

Bookmark: HTML Writer
Note: Stream HTML vanuit FME Flow naar gebruiker
HTML (writer HTML_1)
    attributes: html_content buffer

FME custom transformer JSONTemplaterloop

Input (input)
JSONTemplater
    RESULT_ATTRIBUTE = _result
    VISIBLE_QUERY_VALIDATE = Yes
Input (output)
