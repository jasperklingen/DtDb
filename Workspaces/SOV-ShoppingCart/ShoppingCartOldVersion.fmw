FME workspace ShoppingCartOldVersion.fmw
Title: SetupTreeview

Parameters:
- RelaticsWorkspace =   # Relatics Workspace
- CONFIG = SOV   # Config Name (without .xlsx)
- BatchSize = 0   # Batch Size for Relatics (0 for no batch)

Writers:
- HTML_1: HTML to Tree.html

Bookmark: Query voor het ophalen van de tree
Creator_2
    GEOMTYPE = Geometry Object
    NUM = 1
    CREATED -> FeatureReader [INITIATOR]
FeatureReader
    ATTRS_TO_EXPOSE = Entrycode Filename Operation Order Query QueryEndpoint QueryName
    ATTR_ACCUM_MODE = Only Use Result
    CLIP_TO_ENVELOPE = NO
    COMBINE_GEOM = Use Result
    DATASET = $(FME_SHAREDRESOURCE_DATA)\SOV\Config\$(CONFIG).xlsx
    FEATURETYPES = SOVQuerys
    FORMAT = XLSXR
    INITIATOR_FIRST_OUTPUT = default
    INTERACT = NONE
    ORDER_RESULTS = No
    OUTPUT_ADD_SCHEMA_ATTRIBUTES = NO
    OUTPUT_FEATURES_DISPLAY = Schema and Data Features
    XLSXR_ALLOW_DOLLAR_SIGNS = YES
    XLSXR_APPLY_FILTERS = No
    XLSXR_CASE_SENSITIVE_FEATURE_TYPES = YES
    XLSXR_CONFIGURATION_DATASET = $(FME_MF_DIR)SOV\Config\SOV.xlsx
    XLSXR_CREATE_FEATURE_TABLES_FROM_DATA = Yes
    XLSXR_EXCEL_COL_NAMES = YES
    XLSXR_EXPANDED_DATES_SCANNING = No
    XLSXR_EXPAND_MERGED_CELLS = Yes
    XLSXR_FORCE_DATETIME = NO
    XLSXR_QUERY_FEATURE_TYPES_FOR_MERGE_FILTERS = Yes
    XLSXR_READ_BLANK_AS = Null
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA = SOVQuerys,0,Order,number,2,0,,1,Query,char,2529,,,2,QueryName,char,28,,,3,QueryEndpoint,char,79,,,4,Filename,char,74,,,5,Operation,char,70,,,6,Entrycode,char,32,,,1,,,,NO,NO,1,C:\Users\OscarWillemsAvineon-\Downloads\SOV\Config\SOV.xlsx,"0,0,6,18",Sheet1,NO,NO
    XLSXR_SCHEMA_HANDLING_REVISION = 2
    XLSXR_SKIP_EMPTY_ROWS = YES
    XLSXR_STRIP_SHEETNAME_SPACES = YES
    XLSXR_TABLELIST = SOVQuerys
    XLSXR_TRIM_ATTR_NAME_WHITESPACE = Yes
    XLSXR_USE_CUSTOM_SCHEMA = NO
    <OTHER> -> Tester
Tester
    BOOL_OP = OR
    TEST_CLAUSE = TEST @Value(QueryName) = Tree
    TEST_MODE = TEST
    PASSED -> Sampler
Sampler
    MODE = ORIGINAL
    RATE = 1
    SAMPLE_TYPE_MULTIPLIER = -1
    SAMPLE_MODE = No
    SAMPLE_TYPE_LONG = First N Features
    SAMPLED -> AttributeKeeper
AttributeKeeper
    CREATE_BULK_MODE_FEATURES = NO
    KEEP_ATTRS = Query,QueryEndpoint
    -> AC_Query
AC_Query: AttributeCreator
    ATTR_TABLE = SET_TO query (buffer) = @Value(Query)
    -> HTTPCaller

Bookmark: Tree ophalen
HTTPCaller
    AUTH_METHOD_TYPE = NC
    AUTH_NAMED_CONNECTION = TenneT Laces
    CLIENT_CERTIFICATE_TYPE = NONE
    CONNECTION_TIMEOUT_LENGTH = 60
    CONTENT_TYPE_LOOKUP = application/sparql-query
    CUSTOM_HEADERS = Accept;application/json Accept-Charset;gzip,deflate,br
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(QueryEndpoint)
    TRANSFER_TIMEOUT_LENGTH = 90
    UPLOAD_BODY = @Value(query)
    UPLOAD_TYPE = STRING_UPLOAD
    USE_COOKIES = No
    VERIFY_SSL_CERTIFICATES = No
    AUTH_METHOD = Web Connection
    UPLOAD_CONTENT_TYPE = application/sparql-query
    -> JSONFragmenter
JSONFragmenter
    EXPLODE_FORMAT = JSON
    EXTRACT_ATTR = Yes
    JSON_ATTR = _response_body
    JSON_QUERY = json[*]["bindings"][*]
    READ_FROM_FILE = NO
    RECURSIVE = YES
    REJECT_EMPTY_LISTS = YES
    FRAGMENTS -> AttributeExposer

Bookmark: Maken tabel van tree
AttributeExposer
    ATTR_TABLE = child.value,varchar(61),childName.value,varchar(108),parent.value,varchar(61),parentName.value,varchar(108),childType.value,varchar(200),parentType.value,varchar(200)
    -> BulkAttributeRenamer
BulkAttributeRenamer
    ATTRCHOICE_ACTION = SELECTED
    ATTRLIST = child.value childName.value childType.value parent.value parentName.value parentType.value
    CASE_DISP = YES
    MODE_CHOICE = RENAME
    PATTERN_ACTION_DISP = REMOVESUFFIX
    REPLACE_STR = .value
    ATTRCHOICE = Selected Attributes
    -> InlineQuerier [Relations]
InlineQuerier
    QUERY_DEF:
      Tree,WITH RECURSIVE Tree AS (
        -- Start with root nodes (parents that are not children)
        SELECT
          r."parent" AS rootUri,
          r."parentName" AS rootLabel,
          r."child",
          r."childName",
          1 AS depth,
          r."parentName" <pipe><pipe> '<pipe> ' <pipe><pipe> r."childName" AS path
        FROM relations r
        WHERE r."parent" NOT IN (SELECT "child" FROM relations)

        UNION ALL

        -- Recursive step: join with children
        SELECT
          t.rootUri,
          t.rootLabel,
          r."child",
          r."childName",
          t.depth + 1 AS depth,
          t.path <pipe><pipe> '<pipe> ' <pipe><pipe> r."childName" AS path
        FROM Tree t
        JOIN relations r ON t."child" = r."parent"
      )

      SELECT * FROM Tree
      ORDER BY rootUri, depth;,FIRST
    QUERY_SCHEMA = Tree,rootUri,varchar(61),rootLabel,varchar(108),child,varchar(61),childName,varchar(108),depth,,path,
    TABLE_DEF = Relations,child,varchar(61),childName,varchar(108),childType,varchar(46),parent,varchar(61),parentName,varchar(108),parentType,varchar(46)
    Tree -> StringConcatenator

Bookmark: Maken CSV van tabel
StringConcatenator
    ACTION = Create New Attribute
    PARM_LINE = fme_basicstring:13%1%12:@Value(child),@Value(path)
    VAL_ATTR = _result
    -> Sorter
Sorter
    SORT_PARM = path ALPHA ASCENDING
    SORTED -> Aggregator
Aggregator
    ACCUM_ATTRS = None
    AGGREGATE_TYPE = Homogeneous Collection (If Possible)
    CONCAT_ATTRS = _result
    MODE = Geometry - Assemble One Level
    SEP = "\n"
    AGGREGATE -> AC_header_CSV

Bookmark: HTML pagina maken, CSV tree in de HTML pluggen
AC_header_CSV: AttributeCreator
    ATTR_TABLE:
      SET_TO csv (varchar(200)) = child,path
        @Value(_result)
    -> AC_HTML_JSPagina
AC_HTML_JSPagina: AttributeCreator
    ATTR_TABLE:
      SET_TO html_content (varchar(200)) = <!doctype html>

        <html lang="nl">

        <head>
            <meta charset="utf-8" />
            <title>Shopping Cart</title>
            <meta name="viewport" content="width=device-width, initial-scale=1" />
            <style>
                body {
                    font-family: Arial, sans-serif;
                    padding: 16px;
                }

                h1 {
                    font-size: 1.2rem;
                    margin-bottom: 8px;
                }

                #treeContainer {
                    margin-top: 12px;
                    border: 1px solid #ccc;
                    padding: 8px;
                    border-radius: 6px;
                }

                /* Tree styles with lines */
                ul.treeRoot,
                ul.treeRoot ul {
                    list-style: none;
                    margin: 0;
                    padding-left: 20px;
                    position: relative;
                }

                /* Vertical line for child lists (level 2 and deeper) */
                ul.treeRoot ul::before {
                    content: '';
                    position: absolute;
                    top: 0;
                    left: 8px;
                    bottom: 0;
                    width: 1px;
                    border-left: 1px solid #ccc;
                }

                /* All list items */
                li {
                    position: relative;
                    padding-left: 16px; /* Space for the horizontal connector line */
                }

                /* Horizontal connector line for children (level 2 and deeper) */
                li::before {
                    content: '';
                    position: absolute;
                    top: 12px;
                    left: 0;
                    width: 12px;
                    height: 1px;
                    border-top: 1px solid #ccc;
                }

                /* ================================== */
                /* === FIX: Exclude Top-Level LIs === */
                /* ================================== */

                /* Target the true root LI elements (children of ul.treeRoot) */
                ul.treeRoot > li {
                    padding-left: 0; /* Remove the horizontal padding/indentation */
                }

                /* Remove the horizontal connector line from true root LIs */
                ul.treeRoot > li::before {
                    content: none;
                }

                /* Adjust the vertical line of the UL that is a child of the true root LI
                   to ensure it starts at the top of the UL, not relative to the LI::before */
                ul.treeRoot > li > ul {
                    padding-left: 20px; /* Keep indentation for children */
                }

                ul.treeRoot > li > ul::before {
                    top: 0; /* Ensures the vertical line starts immediately */
                }

                /* ================================== */

                .node {
                    display: flex;
                    align-items: center;
                    gap: 6px;
                    margin: 2px 0;
                }

                .nodeLabel {
                    user-select: none;
                }

                input[type="number"] {
                    width: 72px;
                }

                .section {
                    margin-top: 12px;
                    padding: 6px;
                    border: 1px solid #ddd;
                    border-radius: 6px;
                    background: #f9f9f9;
                }

                button {
                    padding: 8px 12px;
                    border: 1px solid #888;
                    background: #eee;
                    border-radius: 4px;
                    cursor: pointer;
                }

                button:hover {
                    background: #e0e0e0;
                }

                #status {
                    margin-top: 8px;
                    font-weight: bold;
                }

                #webhookList {
                    margin-top: 10px;
                    font-family: monospace;
                    font-size: 0.9em;
                    white-space: pre-wrap;
                    word-break: break-all;
                }

                #webhookList a {
                    display: block;
                    text-decoration: none;
                    color: #0066cc;
                }

                #webhookList a:hover {
                    text-decoration: underline;
                }

                .node span:first-child {
                    width: 12px;
                    display: inline-block;
                }
            </style>
        </head>

        <body>
            <h1>Shopping Cart</h1>

            <div class="explanation" aria-label="explanation">
                <p>Welcome to the shopping cart! Here you can select items and specify the quantity for each option. Each quantity is limited to a maximum of 20. Once you've selected your desired quantities, click "Run" to send the data to the webhook for processing. This will trigger the SOV workspace and send your selected items to the chosen Relatics workspace.</p>
            </div>

            <div class="section" aria-label="Treeweergave">
                <div style="font-weight: bold; margin-bottom: 6px;">Tree view (insert number per option, max 20)</div>
                <div id="treeContainer" aria-label="Treecontainer"></div>
            </div>

            <div class="section" aria-label="Verzending" style="margin-top:12px;">
                <button id="submitBtn">Run</button>
                <div id="status" aria-live="polite"></div>
                <div id="webhookList"></div>
            </div>

            <script>
                const WEBHOOK_URL_TEMPLATE = 'https://tennet.vicrea.nl/fmedatastreaming/SOV/SOV.fmw?CONFIG_XLSX=%24(FME_SHAREDRESOURCE_DATA)%2FSOV%2FConfig%2FSOV.xlsx&SELECTED_GROUP=UUID&COPIES=NUMBEROFCOPIES&HubLaces=&RelaticsWorkspace=RELATICSWORKSPACE&BATCH_SIZE=BatchSize&token=71a7a40d1aa08841162971f44c3e2def76d94767';

                const csvData = `@Value(csv)`; // CSV data comes from FME or backend


                /**
                 * Parses the CSV data into a hierarchical tree structure.
                 * Corrected to handle multiple distinct top-level paths.
                 */
                function parseCsvTree(csv) {
                    const lines = csv.trim().split(/\r?\n/);
                    const dataLines = lines.slice(1).filter(l => l.trim().length > 0);

                    // 1. Introduce a single, virtual 'Root' node to hold all distinct top-level branches
                    const root = { name: 'Tree Root', url: null, path: ['Tree Root'], children: [] };

                    function ensureChild(parent, name, isTopLevel = false) {
                        // Use a simple find on children for efficiency
                        const existing = parent.children.find(c => c.name === name);
                        if (existing) return existing;

                        const newPath = isTopLevel ? [name] : parent.path.concat(name);
                        const child = { name, url: null, path: newPath, children: [] };
                        parent.children.push(child);
                        return child;
                    }

                    for (const raw of dataLines) {
                        const line = raw.trim();
                        const commaIndex = line.indexOf(',');
                        if (commaIndex <= 0) continue;

                        const url = line.substring(0, commaIndex).trim();
                        const path = line.substring(commaIndex + 1).trim();
                        const segments = path.split('<pipe>').map(s => s.trim()).filter(s => s.length > 0);

                        if (segments.length === 0) continue;

                        // Start traversal from the virtual root.
                        let current = root;

                        // 2. The first segment (segments[0]) is a child of the virtual root.
                        // The check is in ensureChild, which guarantees segments[0] is the top level.
                        current = ensureChild(current, segments[0], true);

                        // 3. Process the rest of the segments (if any) as descendants of the top-level node.
                        for (let i = 1; i < segments.length; i++) {
                            current = ensureChild(current, segments[i]);
                        }

                        // 4. Assign the URL to the deepest node.
                        current.url = url;
                    }

                    return root;
                }

                function renderNode(node) {
                    const li = document.createElement('li');

                    const header = document.createElement('div');
                    header.className = 'node';

                    // --- Toggle arrow (only if children exist) ---
                    let toggle = null;
                    if (node.children && node.children.length > 0) {
                        toggle = document.createElement('span');
                        toggle.style.cursor = 'pointer';
                        toggle.style.userSelect = 'none';
                        toggle.style.width = '12px';
                        toggle.style.display = 'inline-block';
                    }

                    // --- Quantity input ---
                    const input = document.createElement('input');
                    input.type = 'number';
                    input.min = 0;
                    input.max = 20;
                    input.value = 0;
                    input.style.width = '72px';

                    const nodeId = node.url ? node.url : ('path:' + (node.path ? node.path.join(' / ') : node.name));
                    input.dataset.nodeId = nodeId;

                    // Limit input to 0–20 live
                    input.addEventListener('input', () => {
                        let v = parseInt(input.value);
                        if (v < 0) input.value = 0;
                        if (v > 20) input.value = 20;
                    });

                    // --- Label ---
                    const label = document.createElement('span');
                    label.className = 'nodeLabel';
                    label.textContent = node.name;

                    if (toggle) {
                        label.style.cursor = "pointer";
                        label.addEventListener("click", () => toggle.click());
                    }

                    // Build header
                    header.appendChild(toggle <pipe><pipe> document.createElement('span')); // empty placeholder when no arrow
                    header.appendChild(input);
                    header.appendChild(label);
                    li.appendChild(header);

                    // --- Render children recursively ---
                    let ul = null;
                    if (node.children && node.children.length > 0) {
                        ul = document.createElement('ul');
                        ul.style.listStyle = 'none';

                        for (const child of node.children) {
                            ul.appendChild(renderNode(child));
                        }
                        li.appendChild(ul);

                        // --- First layer should be open by default ---
                        // NOTE: node.path.length === 1 is TRUE for the actual top-level data nodes
                        const isRoot = node.path && node.path.length === 1;

                        if (isRoot) {
                            ul.style.display = 'block';
                            toggle.dataset.state = 'open';
                            toggle.textContent = '▼';
                        } else {
                            ul.style.display = 'none';
                            toggle.dataset.state = 'closed';
                            toggle.textContent = '▶';
                        }

                        // --- Toggle click handler ---
                        toggle.addEventListener('click', function () {
                            const isOpen = toggle.dataset.state === 'open';
                            toggle.dataset.state = isOpen ? 'closed' : 'open';
                            toggle.textContent = isOpen ? '▶' : '▼';
                            ul.style.display = isOpen ? 'none' : 'block';
                        });
                    }

                    return li;
                }

                // Updated function with virtual root node
                function renderTreeFromData(data) {
                    const rootUl = document.createElement('ul');
                    rootUl.id = 'treeRoot';
                    rootUl.className = 'treeRoot';

                    // Check if the virtual root has children
                    if (data.children && data.children.length > 0) {
                        // Render each top-level branch directly under the root UL
                        for (const child of data.children) {
                            rootUl.appendChild(renderNode(child));
                        }
                    }
                    return rootUl;
                }


                function onNodeValueChange(e) {}

                function loadTree() {
                    const rootNode = parseCsvTree(csvData); // rootNode is the virtual root

                    const container = document.getElementById('treeContainer');
                    container.innerHTML = '';

                    const tree = renderTreeFromData(rootNode);
                    container.appendChild(tree);

                    setStatus('Tree is generated');
                }

                function collectSelectedNodes() {
                    const root = document.getElementById('treeRoot');
                    if (!root) return [];
                    const inputs = root.querySelectorAll('input[type="number"]');
                    const selections = [];
                    inputs.forEach(input => {
                        const val = parseInt(input.value, 10);
                        if (!Number.isNaN(val) && val > 0) {
                            // Store both the ID and the human-readable label
                            selections.push({
                                id: input.dataset.nodeId,
                                label: input.nextSibling.textContent, // span.nodeLabel
                                count: val
                            });
                        }
                    });
                    return selections;
                }


                async function submitWebhook() {
                    const selections = collectSelectedNodes();
                    if (selections.length === 0) {
                        setStatus('Geen geselecteerde nodes met waarde > 0.');
                        return;
                    }

                    const webhookList = document.getElementById('webhookList');
                    webhookList.innerHTML = ''; // Wis vorige resultaten
                    setStatus(`Bezig met verzenden van ${selections.length} item(s)...`);

                    // Verstuur alle webhook-aanroepen (asynchroon, maar zonder wachten op de response)
                    selections.forEach(item => {
                        const url = WEBHOOK_URL_TEMPLATE
                            .replace('SOV.xlsx', encodeURIComponent('$(CONFIG).xlsx'))
                            .replace('UUID', encodeURIComponent(item.id))
                            .replace('RELATICSWORKSPACE', encodeURIComponent('$(RelaticsWorkspace)'))
                            .replace('BatchSize', encodeURIComponent('$(BatchSize)'))
                            .replace('NUMBEROFCOPIES', encodeURIComponent(String(item.count)));

                        // Toon enkel wat er wordt verzonden
                        const message = document.createElement('div');
                        message.textContent = `✔ ${item.label} — ${item.count} stuks verzonden.`;
                        message.style.color = 'green';
                        webhookList.appendChild(message);

                        // Trigger de webhook zonder te wachten op antwoord
                        fetch(url, { method: 'GET' }).catch(err => {
                            console.warn(`Fout bij verzenden van ${item.label}:`, err);
                        });
                    });

                    setStatus(`Verzending afgerond. Totaal ${selections.length} item(s) verstuurd.`);
                }


                function setStatus(msg) {
                    const statusElement = document.getElementById('status');
                    statusElement.textContent = msg;

                    const failedMatch = msg.match(/Mislukt:\s*(\d+)/i);
                    const failedCount = failedMatch ? parseInt(failedMatch[1], 10) : 0;

                    // Set color based on success or failure count
                    statusElement.style.color = failedCount > 0 ? 'red' : 'green';
                }

                document.getElementById('submitBtn').addEventListener('click', submitWebhook);

                loadTree();
            </script>
        </body>

        </html>
    -> HTML (writer HTML_1)

Bookmark: HTML Writer
Note: Stream HTML vanuit FME Flow naar gebruiker
HTML (writer HTML_1)
    attributes: html_content buffer

FME custom transformer JSONTemplaterloop

Input (input)
JSONTemplater
    RESULT_ATTRIBUTE = _result
    VISIBLE_QUERY_VALIDATE = Yes
Input (output)
